module ciena-fib-state {
    namespace   "http://ciena.com/ns/yang/ciena/ciena-fib-state";
    prefix "fib-state";

    import ietf-inet-types {
        prefix inet;
    }

    import ciena-vrf {
        prefix "vrf";
    }

    import ietf-yang-types
    {
        prefix yang;
    }

    organization
        "Ciena Corporation";

    contact
        "Web URL: http://www.ciena.com/
         E-mail:  yang@ciena.com
         Postal:  7035 Ridge Road
                  Hanover, Maryland 21076
                      U.S.A.
         Phone:   +1 800-921-1144
         Fax:     +1 410-694-5750";

    description
        "This YANG module defines Ciena's specific FIB-state yang model.
        Copyright (c) 2020  Ciena Corporation.  All rights
        reserved.
        All information contained herein is, and remains the
        property of Ciena Corporation. Dissemination of this
        information or reproduction of this material is strictly
        forbidden unless prior written permission is obtained
        from Ciena Corporation.";

    revision "2024-02-09" {
        description
            "Updates to FIB neighbor summary to support get all.
             Updates to allow filtered get using both IP address and interface.";
    }

    revision "2023-10-20" {
        description
            "Updated to support FIB neighbor state.";
    }

    revision "2020-08-20" {
        description
            "Initial version of FIB-state model.";
    }

    typedef neighbor-location {
      type enumeration {
         enum local {
            description
               "local neighbor";
         }
         enum remote {
            description
               "remote neighbor";
         }
      }
    }

    typedef neighbor-state {
      type enumeration {
         enum resolved {
            description
               "resolved FIB neighbor";
         }
         enum unresolved {
            description
               "unresolved FIB neighbor";
         }
         enum stale {
            description
               "stale FIB neighbor";
         }
      }
    }

    grouping fib-state-grouping {
        description
            "FIB state attributes";
        container fib-state {
            description
                "FIB state container";
            config false;
            list vrf {
                key "name";
                leaf name {
                    type leafref {
                        path "/vrf:vrf/vrf:vrfName";
                    }
                    description
                        "Routing and forwarding instance name";
                }
                list ipv4 {
                    description
                        "IPv4 routing table";
                    key "destination-prefix protocol";
                    leaf destination-prefix {
                        type union {
                           type inet:ipv4-address;
                           type inet:ipv4-prefix;
                        }
                        description
                            "IPv4 destination prefix or destination address.";
                    }
                    leaf protocol {
                        type enumeration {
                            enum any {
                               description "This IPv4 route is of type any";
                            }
                            enum static {
                               description "This IPv4 route is of type static";
                            }
                            enum connected {
                               description "This IPv4 route is of type connected";
                            }
                        }
                        description
                           "Describes the protocol type of IPv4 route";
                    }
                    list next-hop {
                        key "hierarchy-level identifier";
                        description
                            "Next hop state attributes.
                             A next hop is uniquely identified by combination of
                             hierarchy-level + identifier";
                        leaf hierarchy-level {
                           type uint32;
                           description
                              "Indicates the hierarchy-level of next-hop.";
                        }
                        leaf identifier {
                           type uint32;
                           description
                              "Identifier of next-hop in the list.";
                        }
                        leaf address {
                            type  inet:ip-address;
                            description
                                "IPv4 address";
                        }
                        leaf outgoing-interface {
                            type string;
                            description
                                "Name of the outgoing ip-interface";
                        }
                        leaf installed {
                            type boolean;
                            description
                                "State of route in FIB.
                                 True indicates it was installed in the forwarding plane.
                                 False indicates it was not installed in the forwarding plane.";
                        }
                        leaf active {
                            type boolean;
                            description
                                "Presence indicates this is an active route.";
                        }
                        list mpls-label {
                            key "label-number";

                            leaf label-number {
                               type uint8;
                               description
                                  "Label Number within the mpls-label-stack 1=> outermost, 2=> next etc...";
                            }
                            leaf label {
                               type uint32;
                               description
                                  "Optional MPLS Label value for the MPLS Label within the label stack.";
                            }
                        }
                    }
                }
                list ipv6 {
                    description
                        "IPv6 routing table";
                    key "destination-prefix protocol";
                    leaf destination-prefix {
                        type union {
                           type inet:ipv6-address;
                           type inet:ipv6-prefix;
                        }
                        description
                            "IPv6 destination prefix or destination address.";
                    }
                    leaf protocol {
                        type enumeration {
                            enum any {
                               description "This IPv6 route is of type any";
                            }
                            enum static {
                               description "This IPv6 route is of type static";
                            }
                            enum connected {
                               description "This IPv6 route is of type connected";
                            }
                        }
                        description
                           "Describes the protocol type of IPv6 route";
                    }
                    list next-hop {
                        key "hierarchy-level identifier";
                        description
                            "Next hop state attributes.
                             A next hop is uniquely identified by combination of
                             hierarchy-level + identifier";
                        leaf hierarchy-level {
                           type uint32;
                           description
                              "Indicates the hierarchy-level of next-hop.";
                        }
                        leaf identifier {
                           type uint32;
                           description
                              "Identifier of next-hop in the list.";
                        }
                        leaf address {
                            type  inet:ip-address;
                            description
                                "IPv6 address";
                        }
                        leaf outgoing-interface {
                            type string;
                            description
                                "Name of the outgoing ip-interface";
                        }
                        leaf installed {
                            type boolean;
                            description
                                "State of route in FIB.
                                 True indicates it was installed in the forwarding plane.
                                 False indicates it was not installed in the forwarding plane.";
                        }
                        leaf active {
                            type boolean;
                            description
                                "Presence indicates this is an active route.";
                        }
                        list mpls-label {
                            key "label-number";

                            leaf label-number {
                               type uint8;
                               description
                                  "Label Number within the mpls-label-stack 1=> outermost, 2=> next etc...";
                            }
                            leaf label {
                               type uint32;
                               description
                                  "Optional MPLS Label value for the MPLS Label within the label stack.";
                            }
                        }
                    }
                }
                container summary {
                    config false;
                    description
                        "Summary of all routes";

                    list ip-routes {
                        key "ip-version";
                        description
                            "Statistics of different IP routes";
                        leaf ip-version {
                            type enumeration {
                                enum IPv4 {
                                    description
                                        "The IPv4 protocol as defined in RFC 791";
                                }
                                enum IPv6 {
                                    description
                                        "The IPv6 protocol as defined in RFC 2460";
                                }
                            }
                        }
                        leaf total-route-count {
                            type  uint32;
                            description "Total number of routes in the FIB from all protocols";
                        }
                        leaf static-routes {
                            type  uint32;
                            description "Total number of static routes in the FIB";
                        }
                        leaf connected-routes {
                            type  uint32;
                            description "Total number of connected routes in the FIB";
                        }
                    }
                }
            }
            container fib-neighbor-state
            {
                description
                    "FIB neighbor state container";
                config false;

                list ipv4 {
                    key "ip-address interface-name";

                    leaf ip-address {
                        type inet:ip-address;
                        description
                            "IPv4 address of neighbor";
                    }
                    leaf interface-name {
                        type string;
                        description
                            "Name of the outgoing ip-interface";
                    }
                    leaf mac-address {
                        type yang:mac-address;
                        description
                            "MAC address";
                    }
                    leaf installed {
                        type boolean;
                        description
                            "State of neighbor in FIB.
                                True indicates it was installed in the forwarding plane.
                                False indicates it was not installed in the forwarding plane.";
                    }
                    leaf location {
                        type neighbor-location;
                        description
                            "Indicates the location of a neighbor.";
                    }
                    leaf state {
                        type neighbor-state;
                        description
                            "Indicates the state of a neighbor.";
                    }
                    leaf egress {
                        type string;
                        description
                            "Identifier of the egress associated with a neighbor.";
                    }
                }
                list ipv6 {
                    key "ip-address interface-name";

                    leaf ip-address {
                        type inet:ip-address;
                        description
                            "IPv6 address of neighbor";
                    }
                    leaf interface-name {
                        type string;
                        description
                            "Name of the outgoing ip-interface";
                    }
                    leaf mac-address {
                        type yang:mac-address;
                        description
                            "MAC address";
                    }
                    leaf installed {
                        type boolean;
                        description
                            "State of neighbor in FIB.
                                True indicates it was installed in the forwarding plane.
                                False indicates it was not installed in the forwarding plane.";
                    }
                    leaf location {
                        type neighbor-location;
                        description
                            "Indicates the location of a neighbor.";
                    }
                    leaf state {
                        type neighbor-state;
                        description
                            "Indicates the state of a neighbor.";
                    }
                    leaf egress {
                        type string;
                        description
                            "Identifier of the egress associated with a neighbor.";
                    }
                }
                container summary {
                    config false;
                    description
                        "Summary of all neighbors";

                    list ipv4 {
                        description
                            "Statistics of IPv4 neighbors";
                        key "interface-name";
                        leaf interface-name {
                            type string;
                            description "Interface associated with the IPv4 neighbor entries";
                        }
                        leaf total-neighbor-count {
                            type  uint32;
                            description "Total number of IPv4 neighbors in the FIB";
                        }
                        leaf local-neighbors {
                            type  uint32;
                            description "Total number of local IPv4 neighbors in the FIB";
                        }
                        leaf remote-neighbors {
                            type  uint32;
                            description "Total number of remote IPv4 neighbors in the FIB";
                        }
                    }
                    list ipv6 {
                        description
                            "Statistics of IPv6 neighbors";
                        key "interface-name";
                        leaf interface-name {
                            type string;
                            description "Interface associated with the IPv6 neighbor entries";
                        }
                        leaf total-neighbor-count {
                            type  uint32;
                            description "Total number of IPv6 neighbors in the FIB";
                        }
                        leaf local-neighbors {
                            type  uint32;
                            description "Total number of local IPv6 neighbors in the FIB";
                        }
                        leaf remote-neighbors {
                            type  uint32;
                            description "Total number of remote IPv6 neighbors in the FIB";
                        }
                    }
                }
            }
        }
    }
    uses fib-state-grouping;
}
