module ciena-ietf-alarms {
  namespace "http://www.ciena.com/ns/yang/ciena-ietf-alarms";
  prefix "ciena-ietf-alarms";

  organization
    "Ciena Corporation";

  contact
    "Web URL: http://www.ciena.com/
     E-mail:  yang@ciena.com
     Postal:  7035 Ridge Road
              Hanover, Maryland 21076
              U.S.A.
     Phone:   +1 800-921-1144
     Fax:     +1 410-694-5750";

  description
    "This YANG module defines Ciena's augmentations to the draft-ietf-ccamp-alarm-module-01 model.

     Copyright (c) 2019-2023 Ciena Corporation.  All rights
     reserved.

     All information and intellectual property contained in this
     YANG module (Specification) is, and remains the property
     of Ciena Corporation. Ciena retains all title and ownership
     in the Specification, including any revisions.

     Ciena grants all interested parties that access the
     Specification with the intent to use or distribute (\"you\") a
     non-exclusive, no-cost license to use and distribute
     unmodified copies of the Specification solely in connection
     with the management of Ciena products sold by or on
     behalf of Ciena, provided this copyright notice and license
     appear on all copies. Ciena may rescind or modify this
     license at any time.

     This Specification is supplied 'as is', and Ciena makes no
     warranty, either express or implied, as to the use, operation,
     condition, or performance of the Specification. You agree
     that Ciena has no liability for your use of the Specification.";

  revision "2024-01-04" {
    description
      "Adding new alarm types for external entity.
       Moving the alarm-inventory-changed notification to different yang
       to remove circular dependency";
  }

  revision "2023-11-01" {
    description
     "Adding new alarm type pon-olt-state-change-to-standby";
  }

  revision "2023-10-19" {
    description
    " Adding new alarm type pon-onu-service-config-failure.";
  }

  revision "2023-10-10" {
    description
     "Adding new alarm type tp-corouted-tunnel-oper-state-down.
      Adding new alarm type tp-corouted-tunnel-active.
      Adding new alarm type neighbor discovery exceeded or recovered from 95 percent of the platform capacity.";
  }

  revision "2023-06-06" {
    description
    " Adding new alarm type pon-onu-loss-of-ploam, pon-onu-loss-of-key-synchronization, pon-onu-tx-signal-drift,
      pon-onu-differential-reach, pon-onu-omci-communication-failure, pon-onu-loss-of-signal.";
  }

  revision "2023-04-04" {
    description
    " Adding new alarm type pon-onu-dying-gasp.";
  }

  revision "2023-01-30" {
    description
    " Adding new alarm type pon-statistics-retrieval-threshold.";
  }

  revision "2023-01-12" {
    description
    "Adding new alarm types database-mismatch.
     Adding new alarm types rsvp-tunnel-oper-state-change.
     Adding a new alarm type for license server communication failure.
     Adding new alarm type rsvp-tunnel-delete-alarm.
     Adding new alarm type rsvp-tunnel-mbb-alarm.
     Adding new alarm type chassis-lid-change-alarm.
     Augmented parameters in al:alarm-inventory-changed notification.
     Adding new alarm type isis-te-delay-meas-multi-client.";
  }

  revision "2022-07-08" {
    description
    "Adding new alarm types pon-receive-power-low, pon-receive-power-high, pon-receive-power-warning,
     pon-datalink-rx-errored-bip-blocks, pon-datalink-rx-errored-bip-bit, pon-datalink-rx-hec-errors,
     pon-datalink-rx-crc32-drops, pon-datalink-rx-crc8-errors, pon-datalink-rx-overflow-drops,
     pon-datalink-rx-too-short-drops, datalink-rx-too-long-drops, pon-datalink-rx-fec-uncorrectable-blocks,
     pon-idle-receive-power, pon-transmit-power-low, pon-transmit-power-high, pon-transmit-power-warning,
     pon-rogue-onu, pon-suspect-rogue-onu, cpri-option-mismatch, flexe-protection-group-protection-mode-mismatch,
     flexe-protection-group-channel-mismatch, flexe-protection-group-no-response, flexe-protection-group-aps-loss,
     flexe-bas-oam-rdi, flexe-bas-oam-cs-rf, flexe-bas-oam-cs-lf, pon-physical-equipment-error, pon-self-test-failure,
     pon-temperature-yellow, pon-temperature-red, pon-signal-fail, pon-signal-degrade, pon-laser-bias-current,
     pon-misconfigured-alarm, mgmt-domain-fault.";
  }

  revision "2022-01-20" {
     description
     "Adding new alarm types for shutdown-temp-reached, flexe-bas-oam-los, flexe-bas-oam-remote-fault,
      flexe-bas-oam-local-fault, flexe-bas-oam-period-mismatch, flexe-bas-oam-crc,
      flexe-protection-group-protection-swith, flexe-protection-group-no-active-channel.";
  }

  revision "2021-10-20" {
     description
     "Adding new alarm type macsec-phy-hw-failed.";
  }
  
  revision "2021-07-23" {
     description
     "Adding new alarm type pon-olt-rx-los,
      Adding new alarm type pseudowire-state-down.";
  }

  revision "2021-01-08" {
     description
     "New alarm types for license-expiry-warning, gnss-loss-of-lock, sync-loss-of-lock,
      sync-reference-down, ERPS and CFM alarms, macsec-ca-peer-down, software-download-failed,
      software-install-failed, software-activate-failed, software-remove-failed,
      pon-olt-firmware-mismatch, pon-olt-unreachable, tdm port smart sfp vlan-id-mismatch,
      otu-loss-of-channel-power, ipsec-tunnel-fault, flexe-group-deskew, flexe-group-phy-map-mismatch,
      flexe-port-crc-error, flexe-port-sync-config-mismatch, flexe-port-phy-calendar-A-mismatch,
      flexe-port-phy-calendar-B-mismatch, flexe-port-group-id-mismatch, flexe-port-phy-id-mismatch,
      flexe-port-c-bit-error, flexe-port-loss-of-oh-frame, flexe-port-loss-of-oh-multi-frame,
      flexe-port-oh-block-1-error, flexe-port-remote-phy-failure-error, cfm-l2-loop-active,
      flexe-active-calendar-mismatch.";
  }

  revision "2020-09-10" {
     description
     "New alarm types for bfd-session-down, pon-onu-uni-los, pon-onu-firmware-mismatch.";
  }

  revision "2020-09-02" {
     description
     "New alarm types for interface-fault, isis-adjacency-state, ospf-adjacency-state, bgp-peer-loss, hardware-comp-offline.";
  }

  revision "2020-08-10" {
    description
    "Adding new alarm type pon-onu-deregistered.";
  }

  revision "2020-05-12" {
     description
     "Adding new alarm type ettp-incompatible-speed-capability.";
  }

  revision "2020-04-30" {
    description
      "Adding new alarm types cpu-overload, memory-low, disk-partition-low and ntp-out-of-sync.";
  }

  revision "2020-04-29" {
     description
      "Added new alarm type ettp-loopback-present";
  }

  revision "2020-04-13"{
     description
      "Adding new hw component alarms";
     reference
      "RFC 6020: YANG - A Data Modeling Language for
       the Network Configuration Protocol (NETCONF).
       No specific reference; standard not available.";
  }

  revision "2019-11-04" {
     description
      "Third revision, adding several new alarm types";
    reference
      "RFC 6020: YANG - A Data Modeling Language for
       the Network Configuration Protocol (NETCONF).
       No specific reference; standard not available.";
  }

  revision "2019-06-07" {
    description
      "Second revision, added an alarm to indicate core
       bootstrap not being done.";
    reference
      "RFC 6020: YANG - A Data Modeling Language for
       the Network Configuration Protocol (NETCONF).
       No specific reference; standard not available.";
  }

  revision "2019-01-30" {
    description
      "First revision, to change switch alarm names";
    reference
      "RFC 6020: YANG - A Data Modeling Language for
       the Network Configuration Protocol (NETCONF).
       No specific reference; standard not available.";
  }

  typedef alarm-types {
    type enumeration {
      enum base-alarm {
         value 0;
         description
         "ciena base alarm type. This type wont be used";
      }
      enum test-alarm {
         value 1;
         description
         "This alarm type is only used for testing alarms";
      }
      enum link-fault {
         value 2;
         description
         "Link down alarm";
      }
      enum link-caps-mismatch {
         value 3;
         description
         "Link configuration mismatch with hardware capability";
      }
      enum xcvr-over-temp {
         value 4;
         description
         "Transceiver high temperature threshold crossed";
      }
      enum xcvr-under-temp {
         value 5;
         description
         "Transceiver low temperature threshold crossed";
      }
      enum xcvr-rx-power-hi {
         value 6;
         description
         "Transceiver high rx power threshold crossed";
      }
      enum xcvr-rx-power-lo {
         value 7;
         description
         "Transceiver low rx power threshold crossed";
      }
      enum xcvr-tx-power-hi {
         value 8;
         description
         "Transceiver high tx power threshold crossed";
      }
      enum xcvr-tx-power-lo {
         value 9;
         description
         "Transceiver low tx power threshold crossed";
      }
      enum xcvr-voltage-hi {
         value 10;
         description
         "Transceiver high voltage threshold crossed";
      }
      enum xcvr-voltage-lo {
         value 11;
         description
         "Transceiver low voltage threshold crossed";
      }
      enum xcvr-bias-hi {
         value 12;
         description
         "Transceiver high bias current threshold crossed";
      }
      enum xcvr-bias-lo {
         value 13;
         description
         "Transceiver low bias current threshold crossed";
      }
      enum xcvr-unsupported {
         value 14;
         description
         "Transceiver not in the supported transceiver list";
      }
      enum xcvr-missing {
         value 15;
         description
         "Transceiver has been unplugged";
      }
      enum xcvr-failed {
         value 16;
         description
         "Transceiver has become inaccessible";
      }
      enum hardware-comp-over-temperature {
         value 17;
         description
         "Temperature of the hardware component is at/beyond the maximum temperature threshold";
      }
      enum hardware-comp-under-temperature {
         value 18;
         description
         "Temperature of the hardware component is at/below the minimum temperature threshold";
      }
      enum fan-max-speed {
         value 19;
         description
         "Fan is running at the maximum speed threshold";
      }
      enum fan-min-speed {
         value 20;
         description
         "Fan is running at the minimum speed threshold";
      }
      enum ettp-license-not-activated {
         value 21;
         description
         "Ettp license is not activated";
      }
      enum gear-box-failed {
         value 22;
         description
         "Gear box failed";
      }
      enum primary-switch-not-found {
         value 23;
         description
         "primary switch not found";
      }
      enum support-switch-not-found {
         value 24;
         description
         "support switch not found";
      }
      enum och-rx-loss-of-signal {
         value 25;
         description
         "Optical channel Rx Loss of Signal";
      }
      enum och-rx-loss-of-clock {
         value 26;
         description
         "Optical channel Rx Loss of Clock";
      }
      enum och-tx-loss-of-clock {
         value 27;
         description
         "Optical channel Tx Loss of Clock";
      }
      enum och-rx-power-low {
         value 28;
         description
         "Optical channel Rx Power Low";
      }
      enum och-rx-power-high {
         value 29;
         description
         "Optical channel Rx Power High";
      }
      enum och-tx-power-low {
         value 30;
         description
         "Optical channel Tx Power Low";
      }
      enum och-tx-power-high {
         value 31;
         description
         "Optical channel Tx Power High";
      }
      enum och-loss-of-channel-power {
         value 32;
         description
         "Optical channel Loss of Channel Power";
      }
      enum och-rx-channel-power-low {
         value 33;
         description
         "Optical channel Rx Channel Power Low";
      }
      enum och-rx-channel-power-high {
         value 34;
         description
         "Optical channel Rx Channel Power High";
      }
      enum och-tx-channel-contention {
         value 35;
         description
         "Optical channel Tx Channel Contention";
      }
      enum och-tx-tuning-in-progress {
         value 36;
         description
         "Optical channel Tx Tuning in Progress";
      }
      enum och-tx-prov-required {
         value 37;
         description
         "Optical channel Tx Provisioning required";
      }
      enum och-tx-power-reduction {
         value 38;
         description
         "Optical channel Tx Power Reduction";
      }
      enum och-freq-prov-mismatch {
         value 39;
         description
         "Optical channel Frequency Provisioning Mismatch";
      }
      enum och-laser-freq-out-of-range {
         value 40;
         description
         "Optical channel Laser Frequency Out of Range";
      }
      enum och-rx-freq-out-of-range {
         value 41;
         description
         "Optical channel Rx Frequency Out of Range";
      }
      enum och-tx-freq-out-of-range {
         value 42;
         description
         "Optical channel Tx Frequency Out of Range";
      }
      enum modem-class-mismatch {
         value 43;
         description
         "Modem Class Mismtach";
      }
      enum reach-violation {
         value 44;
         description
         "Reach Violation";
      }
      enum otsi-rdi {
         value 45;
         description
         "Optical Remote Defect Indicator";
      }
      enum spli-dup-discovered {
         value 46;
         description
         "SPLI Duplicate Adjacency discovered";
      }
      enum ptp-disp-scan-in-progress {
         value 47;
         description
         "PTP Dispersion Scan in Progress";
      }
      enum ldc-in-progress {
         value 48;
         description
         "PTP Link Data Retrieval In Progress";
      }
      enum otu-loss-of-frame {
         value 49;
         description
         "OTU Loss of Frame";
      }
      enum otu-loss-of-multiframe {
         value 50;
         description
         "OTU Loss of Multiframe";
      }
      enum otu-loss-frame-and-multiframe {
         value 51;
         description
         "OTU Loss of Frame and Loss of Multiframe";
      }
      enum otu-ais {
         value 52;
         description
         "OTU AIS";
      }
      enum otu-bdi {
         value 53;
         description
         "OTU BDI";
      }
      enum otu-signal-degrade {
         value 54;
         description
         "OTU Signal Degrade";
      }
      enum otu-tti-mismatch {
         value 55;
         description
         "OTU Trace Identifier Mismatch";
      }
      enum otu-pre-fec-signal-degrade {
         value 56;
         description
         "OTU Pre FEC Signal Degrade";
      }
      enum otu-pre-fec-signal-fail {
         value 57;
         description
         "OTU Pre FEC Signal Fail";
      }
      enum odu-lck {
         value 58;
         description
         "ODU LCK";
      }
      enum odu-ais {
         value 59;
         description
         "ODU AIS";
      }
      enum odu-oci {
         value 60;
         description
         "ODU OCI";
      }
      enum odu-bdi {
         value 61;
         description
         "ODU BDI";
      }
      enum odu-signal-degrade {
         value 62;
         description
         "ODU Signal Degrade";
      }
      enum odu-tti-mismatch {
         value 63;
         description
         "ODU Trace Identifier Mismatch";
      }
      enum odu-pti-mismatch {
         value 64;
         description
         "ODU Payload Type Mismatch";
      }
      enum odu-loss-of-multiframe-id {
         value 65;
         description
         "Loss of ODU Multiframe Identifier";
      }
      enum odu-loss-of-lane-alignment {
         value 66;
         description
         "Loss of Lane Alignment";
      }
      enum opu-client-signal-fail {
         value 67;
         description
         "Far End Client Signal Fail";
      }
      enum bandwidth-not-available {
         value 68;
         description
         "Bandwidth Not Available";
      }
      enum module-missing {
         value 69;
         description
         "Module is missing";
      }
      enum module-uninstalled {
         value 70;
         description
         "Module is uninstalled";
      }
      enum module-unsupported {
         value 71;
         description
         "Module is unsupported";
      }
      enum module-mismatch {
         value 72;
         description
         "Module provisioned type does not match actual type";
      }
      enum module-unequipped {
         value 73;
         description
         "Module is unequipped";
      }
      enum module-unlicensed {
         value 74;
         description
         "Module is not licensed";
      }
      enum module-deprovisioned {
         value 75;
         description
         "Module is deprovisioned";
      }
      enum module-prov-fault {
         value 76;
         description
         "Module provisioning has failed";
      }
      enum module-auto-prov-fault {
         value 77;
         description
         "Module auto provisioning has failed";
      }
      enum license-missing {
         value 78;
         description
         "License Missing";
      }
      enum module-down {
         value 79;
         description
         "Module is Down";
      }
      enum post-failure {
         value 80;
         description
         "POST has failed";
      }
      enum sf-faulted {
         value 81;
         description
         "Service Function is in faulted state";
      }
      enum cpu-isolation-failed {
         value 82;
         description
         "CPU isolation failed";
      }
      enum module-faulted {
         value 83;
         description
         "Module is Faulted";
      }
      enum module-init-failure {
         value 84;
         description
         "Module initialization failure";
      }
      enum core-bootstrap-not-done {
         value 85;
         description
         "Core Bootstrap is not done";
      }
      enum sf-audit-failed {
         value 86;
         description
         "Service Function audit failed";
      }
      enum odu-fecsf {
         value 87;
         description
         "OTN Port odu-fecsf.";
      }
      enum opu-plm {
         value 88;
         description
         "OTN Port opu-plm";
      }
      enum odu-loss-of-multiframe {
         value 89;
         description
         "ODU Loss of Multiframe";
      }
      enum xcvr-optic-unrecognized-unqualified {
         value 90;
         description
         "An unrecognized Vendor Transceiver is present.";
      }
      enum xcvr-optic-capability-incompatible {
         value 91;
         description
         "is xcvr optic capability compatible or not";
      }
      enum xcvr-laser-temperature-high-alarm-threshold {
         value 92;
         description
         "Laser Temperature high threshold";
      }
      enum xcvr-laser-temperature-low-alarm-threshold {
         value 93;
         description
         "Laser Temperature low threshold";
      }
      enum xcvr-rx-los {
         value 94;
         description
         "Transceiver detected Rx Loss of Signal.";
      }
      enum hardware-comp-uninstalled {
         value 95;
         description
         "Hardware component is not installed.";
      }
      enum hardware-comp-faulted {
         value 96;
         description
         "Hardware component is faulted";
      }
      enum ettp-incompatible-speed-capability {
         value 97;
         description
         "ETTP Incompatible Speed Capability.";
      }
      enum cpu-overload {
         value 98;
         description
         "CPU is overloaded and high utilization.";
      }
      enum memory-low {
         value 99;
         description
         "Physical memory available is low.";
      }
      enum disk-partition-low {
         value 100;
         description
         "Space available on disk partition is low.";
      }
      enum ntp-out-of-sync {
         value 101;
         description
         "NTP is not synced.";
      }
      enum ettp-loopback-present {
         value 102;
         description
         "ETTP loopback present.";
      }
      enum pon-onu-deregistered {
        value 103;
        description
        "PON ONU has deregistered.";
      }
      enum bgp-peer-loss {
         value 104;
         description
         "BGP peer session is down.";
      }
      enum isis-adjacency-state {
         value 105;
         description
         "ISIS adjacency state.";
      }
      enum hardware-comp-offline {
         value 106;
         description
         "Hardware component is offline.";
      }
      enum ospf-adjacency-state {
         value 107;
         description
         "OSPF adjacency state.";
      }
      enum interface-fault {
         value 108;
         description
         "IP interface is operationally down.";
      }
      enum bfd-session-down {
         value 109;
         description
         "BFD session operational state is down.";
      }
      enum pon-onu-uni-los {
         value 110;
         description
         "PON ONU UNI Port has detected Loss of Signal.";
      }
      enum pon-onu-firmware-mismatch {
        value 111;
        description
        "PON ONU firmware does not match expected version.";
      }
      enum license-expiry-warning {
        value 112;
        description
        "Warning for license expiring.";
      }
      enum gnss-loss-of-lock {
        value 113;
        description
        "GNSS cannot establish lock.";
      }
      enum sync-loss-of-lock {
        value 114;
        description
        "Sync protection group cannot establish lock on the selected input reference.";
      }
      enum sync-reference-down {
        value 115;
        description
        "Sync timing reference is down.";
      }
      enum erps-provision-mismatch {
         value 116;
         description
         "Indicates failure of the G.8032 protocol due to a provisioning mismatch.";
      }
      enum erps-no-raps-pdu-received {
         value 117;
         description
         "The G.8032 protocol is not receiving Ring Automatic Protection Switching
          (R-APS) packets from peer nodes.";
      }
      enum erps-no-rpl-owner {
         value 118;
         description
         "Indicates that the G.8032 ERP-instance (virtual ring)
          is operating without an RPL Owner";
      }
      enum erps-protection-switch-active {
         value 119;
         description
         "Indicates that the G.8032 ERP-instance (virtual ring)
          is operating in protection state";
      }
      enum cfm-remote-rdi {
         value 120;
         description
         "Indicates the aggregate health of the remote MEPs.";
      }
      enum cfm-remote-mac-error {
         value 121;
         description
         "Indicates that one or more of the remote MEPs is
          reporting a failure in its port status TLV or
          interface status TLV.";
      }
      enum cfm-remote-invalid-ccm {
         value 122;
         description
         "Indicates that at least one of the remote MEP
          state machines is not receiving valid CCMs
          from its remote MEP.";
      }
      enum cfm-invalid-ccm {
         value 123;
         description
         "Indicates that one or more invalid CCMs has been
          received and that 3.5 times that CCMs transmission
          interval has not yet expired.";
      }
      enum cfm-cross-connect-ccm {
         value 124;
         description
         "Indicates that one or more cross connect CCMs has been
          received and that 3.5 times of at least one of those
          CCMs transmission interval has not yet expired.";
      }
      enum cfm-max-frame-delay-two-way-threshold {
         value 125;
         description
         "Indicates that maximum two-way delay threshold value is exceeded.";
      }
      enum cfm-average-frame-delay-two-way-threshold {
         value 126;
         description
         "Indicates that average two-way delay threshold value is exceeded.";
      }
      enum cfm-max-inter-frame-delay-variation-two-way-threshold {
         value 127;
         description
         "Indicates that maximum two-way IFDV threshold value is exceeded.";
      }
      enum cfm-average-inter-frame-delay-variation-two-way-threshold {
         value 128;
         description
         "Indicates that average two-way IFDV threshold value is exceeded.";
      }
      enum cfm-measured-fl-forward-threshold {
         value 129;
         description
         "Indicates that forward frame loss threshold value is exceeded.";
      }
      enum cfm-measured-fl-backward-threshold {
         value 130;
         description
         "Indicates that backward frame loss threshold value is exceeded.";
      }
      enum macsec-ca-peer-down {
         value 131;
         description
         "Macsec Connection Association with peer is down.";
      }
      enum software-download-failed {
         value 132;
         description
         "Software download failed.";
      }
      enum software-install-failed {
         value 133;
         description
         "Software install failed.";
      }
      enum software-activate-failed {
         value 134;
         description
         "Software activate failed.";
      }
      enum software-remove-failed {
         value 135;
         description
         "Software remove failed.";
      }
      enum pon-olt-firmware-mismatch {
        value 136;
        description
        "PON OLT firmware does not match expected version.";
      }
      enum pon-olt-unreachable {
        value 137;
        description
        "PON OLT has become unreachable.";
      }
      enum tdm-port-vlan-id-mismatch {
        value 138;
        description
        "Tdm port vlan ID mismatch.";
      }
      enum otu-loss-of-channel-power {
         value 139;
         description
         "Indicates that the optical power is below the loss of channel threshold.
          Only valid if deployed on colorless line.";
      }
      enum ipsec-tunnel-fault {
         value 140;
         description
         "Indicates a fault condition on an IPsec tunnel.";
      }
      enum flexe-port-sync-config-mismatch {
         value 141;
         description
         "FlexE port synchroniztion configuration is out of sync.";
      }
      enum flexe-port-phy-calendar-A-mismatch {
         value 142;
         description
         "FlexE PHY calendar A does not match with peer node.";
      }
      enum flexe-port-group-id-mismatch {
         value 143;
         description
         "FlexE PHY's group ID does not match with peer node.";
      }
      enum flexe-port-phy-id-mismatch {
         value 144;
         description
         "FlexE PHY ID does not match with peer node.";
      }
      enum flexe-port-loss-of-oh-frame {
         value 145;
         description
         "Indicates overhead frame loss on FlexE port.";
      }
      enum flexe-port-loss-of-oh-multi-frame {
         value 146;
         description
         "Indicates overhead multi frame loss on FlexE port.";
      }
      enum flexe-port-c-bit-error {
         value 147;
         description
         "Indicates C bit error on FlexE port.";
      }
      enum flexe-port-crc-error {
         value 148;
         description
         "Indicates CRC error on FlexE port.";
      }
      enum flexe-port-oh-block-1-error {
         value 149;
         description
         "Indicates overhead block 1 error on FlexE port.";
      }
      enum flexe-port-remote-phy-failure-error {
         value 150;
         description
         "Indicates remote PHY failure.";
      }
      enum flexe-group-phy-map-mismatch {
         value 151;
         description
         "Indicates FlexE group has a mismatching PHY map.";
      }
      enum flexe-group-deskew {
         value 152;
         description
         "Indicates FlexE group deskew.";
      }
      enum cfm-l2-loop-active {
         value 153;
         description
         "Indicates the presence of loop in the MEP network
          Alarm would be raised when CFM detects a loop on the MEP,
          and cleared when CFM confirms the absence of the loop";
      }
      enum flexe-port-phy-calendar-B-mismatch {
         value 154;
         description
         "FlexE PHY calendar B does not match with peer node.";
      }
      enum flexe-active-calendar-mismatch {
         value 155;
         description
         "Indicates active calendar (A or B) is not the same as the active calendar at the peer node.";
      }
      
      enum pon-olt-rx-los {
         value 156;
         description
         "PON OLT has detected Rx Loss of Signal.";
      }
      
      enum pseudowire-state-down {
         value 157;
         description
         "Pseudowire operational state is down.";
      }

      enum macsec-phy-hw-failed {
         value 158;
         description
         "MACsec phy HW failed";
      }

      enum shutdown-temp-reached {
         value 159;
         description
         "Temperature of the system is at/beyond the shutdown temperature threshold";
      }
      enum flexe-bas-oam-los {
         value 160;
         description
         "Indicates loss of signal for FlexE BAS OAM";
      }
      enum flexe-bas-oam-remote-fault {
         value 161;
         description
         "Indicates remote fault for FlexE BAS OAM";
      }
      enum flexe-bas-oam-local-fault {
         value 162;
         description
         "Indicates local fault for FlexE BAS OAM";
      }
      enum flexe-bas-oam-period-mismatch {
         value 163;
         description
         "Indicates period mismatch for FlexE BAS OAM";
      }
      enum flexe-bas-oam-crc {
         value 164;
         description
         "Indicates CRC error for FlexE BAS OAM";
      }
      enum flexe-protection-group-protection-switch {
         value 165;
         description
         "Indicates FlexE Protection Group protection switch";
      }
      enum flexe-protection-group-no-active-channel {
         value 166;
         description
         "Indicates working and protecting channels in FlexE Protection Group are inoperative";
      }
      enum pon-receive-power-low {
         value 167;
         description
         "Indicates receive power is below minimum threshold";
      }
      enum pon-receive-power-high {
         value 168;
         description
         "Indicates receive power is above maximum threshold";
      }
      enum pon-receive-power-warning {
         value 169;
         description
         "Indicates receive power is above warning threshold";
      }
      enum pon-idle-receive-power {
         value 170;
         description
         "Indicates idle receive power is not within acceptable range";
      }
      enum pon-datalink-receive-threshold-exceeded {
         value 171;
         description
         "Indicates one or more receive error thresholds have been exceeded on the datalink";
      }
      enum pon-transmit-power-low {
         value 172;
         description
         "Indicates transmit power is below minimum threshold";
      }
      enum pon-transmit-power-high {
         value 173;
         description
         "Indicates transmit power is above maximum threshold";
      }
      enum pon-transmit-power-warning {
         value 174;
         description
         "Indicates transmit power is above warning threshold";
      }
      enum pon-rogue-onu {
        value 175;
        description
        "Indicates the ONU is a confirmed rogue ONU";
      }
      enum pon-suspect-rogue-onu {
        value 176;
        description
        "Indicates the ONU is a suspect rogue ONU";
      }
      enum cpri-option-mismatch {
         value 177;
         description
         "Indicates CPRI option mismatch within DCR group";
      }
      enum flexe-protection-group-protection-mode-mismatch {
         value 178;
         description
         "Indicates locally configured FlexE Protection mode does no match that received through APS messages";
      }
      enum flexe-protection-group-channel-mismatch {
         value 179;
         description
         "Indicates configuration mismatch on working/protection channel";
      }
      enum flexe-protection-group-no-response {
         value 180;
         description
         "Indicates no response to bridge request was received within 50 ms";
      }
      enum flexe-protection-group-aps-loss {
         value 181;
         description
         "Indicates no APS packets received on the protection channel and no other defect is detected";
      }
      enum flexe-bas-oam-rdi {
         value 182;
         description
         "Indicates RDI for FlexE BAS OAM";
      }
      enum flexe-bas-oam-cs-rf {
         value 183;
         description
         "Indicates client signal remote fault for FlexE BAS OAM";
      }
      enum flexe-bas-oam-cs-lf {
         value 184;
         description
         "Indicates client signal local fault for FlexE BAS OAM";
      }
      enum pon-physical-equipment-error {
         value 185;
         description
         "Indicates a physical equipment error has occured";
      }
      enum pon-self-test-failure {
         value 186;
         description
         "Indicates the PON self test has failed";
      }
      enum pon-temperature-yellow {
         value 187;
         description
         "Indicates the PON equipment temperature has turned to yellow";
      }
      enum pon-temperature-red {
         value 188;
         description
         "Indicates the PON equipment temperature has turned to red";
      }
      enum pon-signal-fail {
         value 189;
         description
         "Indicates a PON bit-error rate has exceeded signal-fail threshold";
      }
      enum pon-signal-degrade {
         value 190;
         description
         "Indicates a PON bit-error rate has exceeded signal-degrade threshold";
      }
      enum pon-laser-bias-current {
         value 191;
         description
         "Indicates the laser bias has exceeded the laser bias threshold";
      }
      enum pon-misconfigured-alarm {
         value 192;
         description
         "Indicates a misconfiguration";
      }
      enum mgmt-domain-fault {
         value 193;
         description
         "Indicates that management domain change could not be triggered and restart must be started by the user";
      }

      enum pon-statistics-retrieval-threshold {
         value 194;
         description
         "Indicates too many statistics retrievals are being performed from sensor or gNMI subscriptions. This is
          resulting in heavy CPU usage and action has been taken to drop processing of statistics for a short period of time";
      }

      enum pon-onu-dying-gasp {
         value 195;
         description
         "Indicates the ONU is deregistered due to dying gasp.";
      } 

      enum pon-onu-loss-of-ploam {
         value 196;
         description
         "Indicates the ONU is deregistered due to loss of PLOAM.";
      }

      enum pon-onu-loss-of-key-synchronization {
         value 197;
         description
         "Indicates the ONU is deregistered due to loss of key synchronization.";
      }

      enum pon-onu-tx-signal-drift {
         value 198;
         description
         "Indicates the ONU is deregistered due to TX signal drift.";
      }

      enum pon-onu-differential-reach {
         value 199;
         description
         "Indicates the ONU is deregistered due to differential reach.";
      }

      enum pon-onu-omci-communication-failure {
         value 200;
         description
         "Indicates the ONU is deregistered due to OMCI communication failure.";
      }

      enum pon-onu-loss-of-signal {
         value 201;
         description
         "Indicates LOS on the ONU.";
      }

      enum database-mismatch {
         value 202;
         description
         "Database out of sync";
      }

      enum rsvp-tunnel-oper-state-change {
         value 203;
         description
         "Indicates Rsvp Tunnel operational state.";
      }

      enum license-server-comm-failure {
         value 204;
         description
         "Indicates that external license server is not reachable.";
      }

      enum rsvp-tunnel-delete-alarm {
         value 205;
         description
         "Indicates Rsvp Tunnel delete status.";
      }

      enum rsvp-tunnel-mbb-alarm {
         value 206;
         description
         "Indicates the mbb status of the tunnel.";
      }

      enum chassis-lid-change-alarm {
         value 207;
         description
         "Indicates a chassis lid state change.";
      }

      enum isis-te-delay-meas-multi-client {
         value 208;
         description
         "Indicates that multiple delay measurement clients configured on an IS-IS TE interface.";
      }

      enum pon-onu-service-config-failure {
         value 233;
         description
         "Indicates Service Config failure on the ONU.";
      }

      enum tp-corouted-tunnel-oper-state-down {
         value 234;
         description
         "Indicates MPLS TP Corouted Tunnel operational state.";
      }

      enum tp-corouted-tunnel-active {
         value 235;
         description
         "Indicates MPLS TP Corouted Backup Tunnel active state.";
      }

      enum neighbor-platform-scale-threshold {
         value 238;
         description
         "Neighbor discovery exceeded or recovered from 95 percent of the platform capacity.";
      }

      enum pon-olt-state-change-to-standby {
        value 239;
        description
        "PON OLT state has changed to Standby.";
      }

      enum external-alarm1 {
         value 246;
         description
           "Representing the alarm type for external entity connecting to contact pin 1 of external alarm interface.";
      }

      enum external-alarm2 {
         value 247;
         description
           "Representing the alarm type for external entity connecting to contact pin 2 of external alarm interface.";
      }

      enum external-alarm3 {
         value 248;
         description
           "Representing the alarm type for external entity connecting to contact pin 3 of external alarm interface.";
      }

      enum external-alarm4 {
         value 249;
         description
           "Representing the alarm type for external entity connecting to contact pin 4 of external alarm interface.";
      }

      enum external-alarm5 {
         value 250;
         description
           "Representing the alarm type for external entity connecting to contact pin 5 of external alarm interface.";
      }

      enum external-alarm6 {
         value 251;
         description
           "Representing the alarm type for external entity connecting to contact pin 6 of external alarm interface.";
      }

      enum external-alarm7 {
         value 252;
         description
           "Representing the alarm type for external entity connecting to contact pin 7 of external alarm interface.";
      }

      enum external-alarm8 {
         value 253;
         description
           "Representing the alarm type for external entity connecting to contact pin 8 of external alarm interface.";
      }

      enum external-alarm9 {
         value 254;
         description
           "Representing the alarm type for external entity connecting to contact pin 9 of external alarm interface.";
      }

      enum external-alarm10 {
         value 255;
         description
           "Representing the alarm type for external entity connecting to contact pin 10 of external alarm interface.";
      }

      enum external-alarm11 {
         value 256;
         description
           "Representing the alarm type for external entity connecting to contact pin 11 of external alarm interface.";
      }

      enum external-alarm12 {
         value 257;
         description
           "Representing the alarm type for external entity connecting to contact pin 12 of external alarm interface.";
      }

      enum external-alarm13 {
         value 258;
         description
           "Representing the alarm type for external entity connecting to contact pin 13 of external alarm interface.";
      }

      enum external-alarm14 {
         value 259;
         description
           "Representing the alarm type for external entity connecting to contact pin 14 of external alarm interface.";
      }

      enum external-alarm15 {
         value 260;
         description
           "Representing the alarm type for external entity connecting to contact pin 15 of external alarm interface.";
      }

      enum external-alarm16 {
         value 261;
         description
           "Representing the alarm type for external entity connecting to contact pin 16 of external alarm interface.";
      }
    }
  }

  typedef operator-states  {
    type enumeration {
      enum none {
        value 1;
        description
          "The alarm is not being taken care of.";
      }
      enum ack {
        value 2;
        description
          "The alarm is being taken care of.  Corrective action not
           taken yet, or failed";
      }
      enum closed {
        value 3;
        description
          "Corrective action taken successfully.";
      }
    }
    description
      "Operator states on an alarm.  The 'closed' state indicates
       that an operator considers the alarm being resolved.  This
       is separate from the alarm's 'is-cleared' leaf.";
  }

  rpc set-alarm-operator-state {
    description
      "This operation requests the server to set the operator state to
       one of the value provided.";
    input {
      leaf resource {
        type string;
        description
          "Set operator state for the alarms with this resource.";
      }
      leaf alarm-type-id {
        type alarm-types;
        description
          "Set operator state for the alarms with this alarm-type-id.";
      }
      leaf alarm-type-qualifier {
        type string;
        description
          "Set operator state for the alarms with this alarm-type-qualifier.";
      }
      leaf state {
        type operator-states;
        mandatory true;
        description
          "Set this operator state.";
      }
      leaf text {
        type string;
        description
          "Additional optional textual information.";
      }
    }
    output {
      leaf modified-alarms {
        type uint32;
        description
          "Number of alarm entries whose operator state has been set.";
      }
    }
  }
}
