module ciena-macsec-deviation {
    yang-version 1.1;
  namespace "http://www.ciena.com/ns/yang/ciena-macsec-deviation";
  prefix "cn-macsec-deviation";

  import ciena-macsec { 
     prefix "cn-macsec"; 
  }

  organization
     "Ciena Corporation";

  contact
     "Web URL: http://www.ciena.com/
     E-mail:  yang@ciena.com
     Postal:  7035 Ridge Road
     Hanover, Maryland 21076
     U.S.A.
     Phone:   +1 800-921-1144
     Fax:     +1 410-694-5750";

  description
     "This YANG module defines Ciena's specific deviations 
      MAC Security 802.1AE.

      Copyright (c) 2023 Ciena Corporation.  All rights 
      reserved.
      
      All information contained herein is, and remains the
      property of Ciena Corporation. Dissemination of this 
      information or reproduction of this material is strictly
      forbidden unless prior written permission is obtained 
      from Ciena Corporation.";

  revision 2022-09-27 {
    description
      "This YANG model describes the deviation of ciena-macsec yang";
  }

  deviation /cn-macsec:macsec/cn-macsec:config/cn-macsec:connection-association/cn-macsec:delay-protection-on {
    deviate not-supported;
  }

} // ciena-macsec-deviation
