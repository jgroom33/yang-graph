/*
* File name : ciena-l3-types.yang
*/

module ciena-l3-types {
    yang-version 1.1;
    namespace   "urn:ciena:params:xml:ns:yang:ciena:ciena-types";
    prefix "cn-l3-types";

    import ietf-inet-types {
        prefix inet;
    }

    organization
        "Ciena Corporation";

    contact
        "Web URL: http://www.ciena.com/
         E-mail:  yang@ciena.com
         Postal:  7035 Ridge Road
                  Hanover, Maryland 21076
                     U.S.A.
         Phone:   +1 800-921-1144
         Fax:     +1 410-694-5750";

    description
      "This YANG module defines Ciena's l3 type

      Copyright (c) 2022  Ciena Corporation.  All rights
      reserved.

      All information and intellectual property contained in this
      YANG module (Specification) is, and remains the property
      of Ciena Corporation. Ciena retains all title and ownership
      in the Specification, including any revisions.

      Ciena grants all interested parties that access the
      Specification with the intent to use or distribute (you) a
      non-exclusive, no-cost license to use and distribute
      unmodified copies of the Specification solely in connection
      with the management of Ciena products sold by or on
      behalf of Ciena, provided this copyright notice and license
      appear on all copies. Ciena may rescind or modify this
      license at any time.

      This Specification is supplied 'as is', and Ciena makes no
      warranty, either express or implied, as to the use, operation,
      condition, or performance of the Specification. You agree
      that Ciena has no liability for your use of the Specification.";

    revision "2024-01-09" {
      description
         "Added OSPF-GR status types.
          Updated help description of Local-AS for well-known-community-type attribute.";
    }

    revision "2023-05-31" {
      description
         "Added replace-as support for local-as-option.
          Added new typedef for extended community-rt-max, to extend support for RT-2 and up to 20 RT values.
          Updated the extended community-rt-max typedef pattern to address 4byte ASN error case.
          Added transport RSVP-TE in transport type. ";
    }

    revision "2023-05-08" {
      description
        "Added pcep authentication mode types.
         Added assoc-types and sync-state.
         Added enum type aigp-metric-type.
         Added enum evpn-rt5-type to advertise VPNv4 or VPNv6.
         Added enum type for EVPN route types.
         Added RSVP-TEv4 as an additional AFI type for use in MPLS.
         Added a new typedef to support max string length of 255 characters.
         Removed enum value p2p in isis-iflevel.";
    }

    revision "2022-09-22" {
        description
            "Add typedefs for PIM.
             Added a typedef for clear rpc update-group-counter for BGP.
             Added a typedef for BGP large community value that identifies 12 octet
             BGP large community value.
             Added Segment Routing SID types.
             Added enum type to support OSPFV3.
             Added event types for multicast routes.
             Added PW mode tdm_crossconnect to support tdm cross-connect PW.
             Added enum type clear-bgp-redistribute-type for clear bgp redistribute command.
             Added a type 1 format for site of origin for BGP.
             Updated the std-community-type typedef pattern and length.
             Updated the large-community-type typedef pattern.
             Added if feature support for segment routing label block.
             Added a new typedef to support max string length of 680 characters.";
    }


    revision "2022-06-29" {
        description
            "Updated Segment Routing SID types.";
    }

    revision "2022-03-21" {
        description
            "Added enum type to support transit tunnel stats.
             Added operation template type enum for transport selection.
             Added enum type to support BGP LS.
             Added type definition for cross-connect entry flags to distinguish state of forwarding entry.
             Adding rsvp ingress unidirectional enum for tunnel type.";
    }

    revision "2021-10-01" {
        description
            "Added MPLS IAS VPNv6 AFI type to FTN/ILM table.
             Added label management mode types.
             Added enums for ISIS microloop event-type.";
    }

    revision "2021-09-20" {
        description
            "Added a typedef for VPLS ID which is a BGP extended community value that identifies
             the VPLS domain.";
    }

    revision "2021-07-28" {
        description
            "Added reason codes for EVPN EVLAG protection switch over and Ethernet segment fault.
             Added transport type enum for transport selection.";
    }

    revision "2021-07-14" {
        description
            "Added the new enum(redistribute) in BGP clear-type which is the option
             to initiate the refresh of redistributed routes from RIB.";
    }

    revision "2021-03-17" {
        description
            "Added SR policy grouping and fallback-state type for SR policy color.
             Added enums for MPLS label range to support rsvp,srgb,srlb,staticVc and staticTunnel.
             Added MPLS AFI type enum for FTN/ILM.
             Adding support for clear BGP all soft counters.
             Added VRF event type and VRF reason type enum for VRF route threshold values.";
    }
    revision "2020-08-31" {
        description
            "Added IPv6 enum in mode type to support IPv6 prefix-list.
             Added ISIS topology type enum.
             Added ISIS enum in ospf-route-source to support ISIS to OSPF redistribution.
             Added AFI/SAFI types for bgp table-map test.
             Added PW mode type switching to support multi-segment PW.";
    }

    revision "2020-02-10" {
        description
            "Supporting OSPF SR-Extensions, LDP IGP sync, TI-LFA and  RLFA
             Added Changes for Ospf Virtual link feature
             Adding local-as options types: no-prepend
             Adding support for BGP/OSPF route redistribution
             Added Changes for Ospf Virtual link feature.
             Supporting OSPF LDP IGP sync and remote LFA.
             Supporting OSPF specific match and set filters for Route Map.
             Changing bit values to start from 0 as per RFC-7950.
             Adding sr policy enum for tunnel type.";
    }
    
    revision "2020-01-23" {
        description
            "Supporting extended area-id as per IETF.
             Added protocol enum type for prefix-lists.";
    }

    revision "2018-04-05" {
        description
            "Initial version of ciena data types.";
    }
	
    feature rsvp {
     description
        "RSVP protocol label-range";
    }
	
    feature static-vc {
     description
        "Static VC protocol label-range";
    }

    feature pim-dm {
        description
           "Support the PIM dense-mode protocol.";
    }

    feature pim-smdm {
        description
           "Support the combined PIM sparse-mode and dense-mode protocol.";
    }

    feature srlb {
        description
            "Support SRLB protocol.";
    }

    /* BGP data types */
    typedef cluster-id {
        type union{

            type inet:ipv4-address {

            }
            type uint32 {
                range "1..4294967295";

            }
        }
    }

    typedef bgp-med-type {
        type enumeration {
            enum confed { value 0;    }
        }
    }

    typedef bgp-add-path-type {
        type bits {
            bit receive { position 0;  }
            bit send { position 1;  }
        }
    }

    typedef bgp-peer-add-path-type {
        type enumeration {
            enum receive { value 1;    }
            enum send { value 2;    }
            enum send-receive { value 3;    }
            enum disable { value 4;    }
        }
    }

    typedef bgp-redistribute-type {
        type enumeration {
            enum kernel { value 1;    }
            enum connected { value 2;    }
            enum static { value 3;    }
            enum rip { value 4;    }
            enum isis { value 6;    }
            enum ospf {
               description
                 "Redistribute OSPF into BGP.";
               value 5;
            }
        }
    }

    typedef redist-ospf-type {
        type enumeration {
            enum ospf { value 5;    }
        }
    }

    typedef afi-type {
        type enumeration {
            enum ipv4 {
                value 1;
                description "Specifies an IPv4 afi-type";
            }
            enum ipv6 {
                value 2;
                description "Specifies an IPv6 afi-type";
            }
            enum vpnv4 {
                value 3;
                description "Specifies a VPNv4 afi-type";
            }
            enum vpnv6 {
                value 4;
                description "Specifies a VPNv6 afi-type";
            }
            enum rtfilter {
                value 5;
                description "Specifies a rtfilter afi-type";
            }
            enum l2vpn {
                value 25;
                description "Specifies a l2VPN afi-type";
            }
            enum link-state {
                value 16388;
                description "Specifies a link-state afi-type";
            }
            enum all {
                value 0;
                description "Specifies an all afi-type";
            }
        }
    }

    typedef safi-type {
        type enumeration {
            enum unicast {
                value 1;
                description "Specifies an unicast safi-type";
            }
            enum multicast {
                value 2;
                description "Specifies a multicast safi-type";
            }
            enum labeled-unicast {
                value 4;
                description "Specifies a labeled-unicast safi-type";
            }
            enum l2vpn-vpls {
                value 65;
                description "Specifies a l2vpn-vpls safi-type";
            }
            enum evpn {
                value 70;
                description "Specifies an evpn safi-type";
            }
            enum vpn-unicast {
                value 128;
                description "Specifies a vpn-unicast safi-type";
            }
            enum rtfilter-unicast {
                value 132;
                description "Specifies a rtfilter-unicast safi-type";
            }
            enum link-state {
                value 71;
                description "Specifies a link-state safi-type";
            }
            enum all {
                value 0;
                description "Specifies an all safi-type";
            }
        }
    }

    typedef vrf-afi-type {
        type enumeration {
            enum ipv4 { value 1;    }
            enum ipv6 { value 2;    }
        }
    }

    typedef vrf-safi-type {
        type enumeration {
            enum unicast { value 1;    }
        }
    }

    typedef adjacency-table-type {
       type enumeration {
           enum none { value 0;  }
           enum in { value 1;   }
           enum out { value 2;   }
           enum all { value 3;   }
       }
    }

    typedef clear-type {
       type enumeration {
           enum all { value 0;   }
           enum peer { value 1;   }
           enum group { value 2;   }
           enum external { value 3;   }
           enum as { value 4;   }
           enum rfd { value 5;  }
           enum prefix { value 6;  }
           enum redistribute { value 7;  }
           enum update-group-counter { value 8;  }
       }
    }

    typedef clear-bgp-redistribute-type {
       description
           "BGP redistribute protocol types for clear bgp redistribute";
       type enumeration {
           enum all {
               description
                 "Clear all redistributed routes";
               value 0;
           }

           enum connected {
               description
                 "Clear redistributed connected routes";
               value 1;
           }

           enum static {
               description
                 "Clear redistributed static routes";
               value 2;
           }

           enum isis {
               description
                 "Clear all redistributed routes from all ISIS instances";
               value 3;
           }

           enum ospf {
               description
                 "Clear redistributed OSPF routes";
               value 4;
           }
       }
    }

    typedef clear-soft {
       type enumeration {
           enum none { value 1;   }
           enum out { value 2;   }
           enum in { value 3;   }
           enum both { value 4;   }
           enum in-orf-prefix { value 5;   }
           enum table-map { value 6;  }
           enum rfd-damp { value 7;  }
           enum rfd-flap-stat { value 8;  }
       }
    }
    typedef aigp-metric-cost {
        type enumeration {
            enum pre-bestpath { value 128;    }
            enum igp-cost { value 129;    }
        }
    }

    typedef bgp-send-community-type {
        type bits {
            bit standard { position 0;  }
            bit extended { position 1;  }
            bit both { position 2;  }
        }
    }

    typedef attr-unchanged-type {
        type bits {
            bit as-path { position 0;  }
            bit next-hop { position 1;  }
            bit med { position 2;  }
        }
    }

    typedef bgp-orf-prefix-type {
        type enumeration {
            enum both { value 0;    }
            enum receive { value 1;    }
            enum send { value 2;    }
        }
    }

    typedef bgp-rmap-direction {
        type enumeration {
            enum in { value 0;    }
            enum out { value 1;    }
        }
    }

    typedef bgp-distribute-list-action {
        type bits {
            bit in { position 0;  }
            bit out { position 1;  }
        }
    }

    typedef bgp-community-list-action {
        type enumeration {
            enum deny { value 1;    }
            enum permit { value 2;    }
        }
    }

     typedef bgp-rd {
       type string {
         pattern
           '(0:(6553[0-5]|655[0-2]\d|65[0-4]\d{2}|6[0-4]\d{3}|'
         + '[0-5]?\d{1,3}\d|[1-9]):(429496729[0-5]|42949672[0-8]\d|'
         + '4294967[01]\d{2}|429496[0-6]\d{3}|42949[0-5]\d{4}|'
         + '4294[0-8]\d{5}|429[0-3]\d{6}|42[0-8]\d{7}|4[01]\d{8}|'
         + '[0-3]?\d{1,8}\d|[1-9]))|'
         + '(1:(((\d|[1-9]\d|1\d{2}|2[0-4]\d|25[0-5])\.){3}(\d|[1-9]\d|'
         + '1\d{2}|2[0-4]\d|25[0-5])):(6553[0-5]|655[0-2]\d|'
         + '65[0-4]\d{2}|6[0-4]\d{3}|[0-5]?\d{1,3}\d|[1-9]))|'
         + '(2:(429496729[0-5]|42949672[0-8]\d|4294967[01]\d{2}|'
         + '429496[0-6]\d{3}|42949[0-5]\d{4}|4294[0-8]\d{5}|'
         + '429[0-3]\d{6}|42[0-8]\d{7}|4[01]\d{8}|[0-3]?\d{1,8}\d|[1-9]):'
         + '(6553[0-5]|655[0-2]\d|65[0-4]\d{2}|6[0-4]\d{3}|'
         + '[0-5]?\d{1,3}\d|[1-9]))|'
         + '(([3-9a-fA-F]|[1-9a-fA-F][\da-fA-F]{1,3}):'
         + '[\da-fA-F]{1,12})';
       }
       description
         "A route distinguisher is an 8-octet value used to distinguish
          routes from different BGP VPNs (RFC 4364). A route
          distinguisher consists of three fields: A 2-octet type field,
          an administrator field, and an assigned number field.
          According to the data formats for type 0, 1, and 2 defined in
          RFC4364, the encoding pattern is defined as:

          0:2-octet-asn:4-octet-number
          1:4-octet-ipv4addr:2-octet-number
          2:4-octet-asn:2-octet-number.
          2-octet-other-hex-number:6-octet-hex-number

          Some valid examples are: 0:100:100, 1:1.1.1.1:100, and
          2:1234567890:203.";
       reference
         "RFC4364: BGP/MPLS IP Virtual Private Networks (VPNs).";
     }

     typedef bgp-rt {
       type string {
         pattern
           '(0:(6553[0-5]|655[0-2]\d|65[0-4]\d{2}|6[0-4]\d{3}|'
         + '[0-5]?\d{1,3}\d|[1-9]):(429496729[0-5]|42949672[0-8]\d|'
         + '4294967[01]\d{2}|429496[0-6]\d{3}|42949[0-5]\d{4}|'
         + '4294[0-8]\d{5}|429[0-3]\d{6}|42[0-8]\d{7}|4[01]\d{8}|'
         + '[0-3]?\d{1,8}\d|[1-9]))|'
         + '(1:(((\d|[1-9]\d|1\d{2}|2[0-4]\d|25[0-5])\.){3}(\d|[1-9]\d|'
         + '1\d{2}|2[0-4]\d|25[0-5])):(6553[0-5]|655[0-2]\d|'
         + '65[0-4]\d{2}|6[0-4]\d{3}|[0-5]?\d{1,3}\d|[1-9]))|'
         + '(2:(429496729[0-5]|42949672[0-8]\d|4294967[01]\d{2}|'
         + '429496[0-6]\d{3}|42949[0-5]\d{4}|4294[0-8]\d{5}|'
         + '429[0-3]\d{6}|42[0-8]\d{7}|4[01]\d{8}|[0-3]?\d{1,8}\d|[1-9]):'
         + '(6553[0-5]|655[0-2]\d|65[0-4]\d{2}|6[0-4]\d{3}|'
         + '[0-5]?\d{1,3}\d|[1-9]))';
       }
       description
         "A route target is an 8-octet BGP extended community
          initially identifying a set of sites in a BGP
          VPN (RFC 4364). However, it has since taken on a more
          general role in BGP route filtering.
          A route target consists of three fields:
          a 2-octet type field, an administrator field,
          and an assigned number field.
          According to the data formats for type 0, 1, and 2 defined in
          RFC4360 and RFC5668, the encoding pattern is defined as:

          0:2-octet-asn:4-octet-number
          1:4-octet-ipv4addr:2-octet-number
          2:4-octet-asn:2-octet-number.
          Some valid examples are: 0:100:100, 1:1.1.1.1:100, and
          2:1234567890:203.";
       reference
         "RFC4360: BGP Extended Communities Attribute.
          RFC5668: 4-Octet AS Specific BGP Extended Community.";
     }

    typedef bgp-gr-mode {
        type enumeration {
            enum disable { value 0;    }
            enum enable { value 1;    }
        }
    }

    typedef bgp-local-as-types {
        type bits {
            bit no-prepend { position 0;  }
            bit replace-as { position 1;  }
        }
        description
            "Local-as types no-prepend,replace-as, to not allow prepending local-as and trueAS 
             respectively from the as path updates.";
    }

    typedef bgp-vpls-id {
       type string {
         pattern
           '(0:(6553[0-5]|655[0-2]\d|65[0-4]\d{2}|6[0-4]\d{3}|'
         + '[0-5]?\d{1,3}\d|[1-9]):(429496729[0-5]|42949672[0-8]\d|'
         + '4294967[01]\d{2}|429496[0-6]\d{3}|42949[0-5]\d{4}|'
         + '4294[0-8]\d{5}|429[0-3]\d{6}|42[0-8]\d{7}|4[01]\d{8}|'
         + '[0-3]?\d{1,8}\d|[1-9]))|'
         + '(1:(((\d|[1-9]\d|1\d{2}|2[0-4]\d|25[0-5])\.){3}(\d|[1-9]\d|'
         + '1\d{2}|2[0-4]\d|25[0-5])):(6553[0-5]|655[0-2]\d|'
         + '65[0-4]\d{2}|6[0-4]\d{3}|[0-5]?\d{1,3}\d|[1-9]))|'
         + '(2:(429496729[0-5]|42949672[0-8]\d|4294967[01]\d{2}|'
         + '429496[0-6]\d{3}|42949[0-5]\d{4}|4294[0-8]\d{5}|'
         + '429[0-3]\d{6}|42[0-8]\d{7}|4[01]\d{8}|[0-3]?\d{1,8}\d|[1-9]):'
         + '(6553[0-5]|655[0-2]\d|65[0-4]\d{2}|6[0-4]\d{3}|'
         + '[0-5]?\d{1,3}\d|[1-9]))|'
         + '(([3-9a-fA-F]|[1-9a-fA-F][\da-fA-F]{1,3}):'
         + '[\da-fA-F]{1,12})';
       }
       description
         "A VPLS ID is a BGP extended community value that identifies the VPLS domain. 
          Manual configuration of this ID is optional because a default VPLS ID is generated 
          using the BGP autonomous system number and the configured VPN ID.
          A VPLS ID can be composed in one of three ways: a 2-octet type field with
          an autonomous system number and an arbitrary number or an IP address and 
          an arbitrary number.
          According to the data formats for type 0, 1, and 2 defined in
          RFC4360 and RFC5668, the encoding pattern is defined as:

          For example:
          0:2-octet-asn:4-octet-number
          1:4-octet-ipv4addr:2-octet-number
          2:4-octet-asn:2-octet-number.

          Some valid examples are: 0:100:100, 1:1.1.1.1:100, and
          2:1234567890:203.";
        reference
         "RFC4360: BGP Extended Communities Attribute.
          RFC5668: 4-Octet AS Specific BGP Extended Community.
          RFC6074: Provisioning, Auto-Discovery, and Signaling
          in Layer 2 Virtual Private Networks (L2VPNs).";
     }

    /* ISIS Datatypes */
    typedef system-id {
        type string {
            pattern
                '[0-9A-Fa-f]{4}\.[0-9A-Fa-f]{4}\.[0-9A-Fa-f]{4}';
            }
            description
                "This type defines IS-IS system-id using pattern,
               An example system-id is 0143.0438.AeF0";
    }

    typedef net {
        type string {
            pattern
               '[0-9A-Fa-f]{2}(\.[0-9A-Fa-f]{4}){0,6}.[0-9A-Fa-f]{4}\.[0-9A-Fa-f]{4}\.[0-9A-Fa-f]{4}\.[0]{2}';
            }
            description
                "This type defines IS-IS net using pattern";
    }

	 typedef  sr-enable-disable{
        type enumeration {
            enum disable { value 0;    }
            enum enable { value 1;    }
        }
     }

	 typedef  isis-address-ipv6{
        type enumeration {
            enum ipv6 { value 1;    }
        }
    }

    typedef  isis-origin-type{
        type enumeration {
            enum originate { value 4;    }
            enum originate-always { value 32;    }
        }
    }


    typedef  protocol-name {
         type enumeration {
            enum connected { value 1;    }
            enum static { value 2;    }
            enum ospf { value 3;    }
            enum bgp { value 4;    }
         }
     }


    typedef  type {
         type enumeration {
            enum 1to2 { value 1;    }
            enum 2to1 { value 2;    }
         }
     }


	 typedef  isis-summary-level{
        type enumeration {
            enum level-1 { value 1;    }
            enum level-2 { value 2;    }
            enum level-1-2 { value 3;    }
        }
    }

    typedef  isis-level-types{
        type enumeration {
            enum level-1 { value 1;    }
            enum level-2 { value 2;    }
            enum level-1-2 { value 3;    }
        }
    }

    typedef  metric-style{
        type enumeration {
            enum wide { value 1;    }
        }
    }

    typedef  isis-level-type{
        type enumeration {
            enum level-1 { value 1;    }
            enum level-2 { value 2;    }
        }
    }

    typedef  isis-auth-mode{
        type enumeration {
            enum md5 { value 1;    }
            enum text { value 2;    }
        }
    }

    typedef pcep-auth-mode{
      type enumeration {
        enum md5 {
          value 1;
          description
            "Authentication mode as md5.";
        }
      }
    }

    typedef  isis-snp{
        type enumeration {
            enum send-only { value 1;    }
            enum validate { value 2;    }
        }
    }

    typedef  isis-level-proto{
        type enumeration {
            enum ipv4 { value 1;    }
            enum ipv6 { value 2;    }
        }
    }

    typedef  isis-ip-address-family {
        type enumeration {
            enum ipv4 { value 1;    }
// not for 10.2  enum ipv6 { value 2;    }
        }
    }

    typedef  isis-frr-enum{
        type enumeration {
            enum all { value 1;    }
        }
    }

    typedef  isis-frr-tie-breaker {
        type enumeration {
            enum primary-path { value 1; }
            enum node-protecting { value 3; }
            enum secondary-path { value 5; }
            enum downstream-path { value 6; }
        }
    }

    typedef  isis-rlfa-protection-type {
        type enumeration {
            enum downstream-protection { value 1; }
        }
    }

    typedef  isis-suppress{
        type enumeration {
            enum external { value 1;    }
            enum interlevel { value 2;    }
            enum external-interlevel { value 3;    }
            enum interlevel-external { value 4;    }
        }
    }

    typedef  isis-onstartup{
        type enumeration {
            enum wait-for-bgp { value 1;    }
		      enum time-out { value 2;    }
          }
    }

    typedef  isis-state{
        type enumeration {
            enum Down { value 0;    }
            enum Init { value 1;    }
            enum Up { value 2;    }
        }
    }

    typedef  isis-nbr-adj{
        type enumeration {
            enum Suppress { value 1;    }
            enum Advertise { value 2;    }
        }
    }

    typedef  isis-iflevel{
        type enumeration {
            enum level-1 { value 1;    }
            enum level-2 { value 2;    }
        }
    }

    typedef  isis-interface-type{
        type enumeration {
            enum broadcast { value 1;    }
            enum point-to-point { value 2;    }
        }
    }

    typedef  mesh-blocked{
        type enumeration {
            enum blocked { value 0;    }
        }
    }

    typedef  isis-mesh-type{
        type union{

            type mesh-blocked {

            }
            type uint32 {
                range "1..4294967295";

            }
        }
    }

    typedef  isis-sync-type{
        type enumeration {
            enum level-1 { value 1;    }
            enum level-2 { value 2;    }
            enum level-1-2 { value 3;    }
        }
    }

	typedef  isis-route-type{
		type enumeration {
			enum redistribution {
				value 1;
				description "Clear ISIS IP local redistribution routes";
			}
			enum all {
				value 2;
				description "all of the IS-IS routing table";
			}
		}
	}

    typedef isis-distribute-type{
        type enumeration {
            enum bgp-ls {
                value 1;
                description "Link State distribution to BGP";
            }
        }
    }

    typedef isis-topology-type {
        type enumeration {
            enum single-topology { 
               description
                  "IS-IS single topology running.";
               value 1;
            }
            enum multi-topology {
               description
                  "IS-IS multi topology running.";
               value 2; 
            }
        }
    }

	 typedef  ipv4-addr{
        type inet:ipv4-address;
    }

    typedef  ipv6-addr{
        type inet:ipv6-address;
    }

    typedef  ip-addr{
        type union{

            type ipv4-addr {

            }
            type ipv6-addr {

            }
        }
    }

    typedef  isis-debug{
        type bits {
            bit ifsm { position 0;  }
            bit nfsm { position 1;  }
            bit pdu { position 2;  }
            bit lsp { position 3;  }
            bit spf { position 4;  }
            bit events { position 5;  }
            bit nsm { position 6;  }
            bit checksum { position 7;  }
            bit authentication { position 8;  }
            bit local-updates { position 9;  }
            bit protocol-errors { position 10;  }
            bit bfd { position 12;  }
            bit mpls { position 13;  }
            bit rib { position 14;  }
            bit sr { position 15;  }
            bit lfa { position 16;  }
            bit spf-trace { position 17;  }
        }
    }

    typedef  isis-cspf-debug{
        type bits {
            bit events { position 0;  }
            bit hexdump { position 1;  }
        }
    }

   typedef  rt-direction{
        type enumeration {
            enum import { value 0;    }
            enum export { value 1;    }
            enum both { value 2;    }
        }
    }

    typedef isis-afi-type {
        type enumeration {
            enum ipv4 {
              value 1;
              description
                "IS-IS Address-family IPv4 support";
            }
            enum ipv6 {
              value 2;
              description
                "IS-IS Address-family IPv6 support";
            }
        }
        description
           "IS-IS Address-family type";
    }

    typedef isis-safi-type {
        type enumeration {
            enum unicast {
              value 1;
              description
                "IS-IS Sub-Address-family Unicast support";
            }
        }
        description
           "IS-IS Sub-Address-family type";
    }
    
    typedef  isis-v6-origin-type{
        type enumeration {
            enum originate {
                value 4;
                description
                  "Originate reachability information to Default destination into LSP";
            }
        }
    }
    
    typedef  isis-microloop-event-type {
        type enumeration {
            enum none { 
                value 0;
                description
                  "No events have been detected";
            }
            enum local-link-down { 
                value 1;
                description
                  "Local link or neighbor has gone down.";
            }
            enum remote-link-down {
                value 2;
                description
                  "Remote link has gone down.";
            }
            enum remote-link-up{
                value 3;
                description
                  "Remote link has gone up.";
            }
        }
    }

 /* MPLS-LDP Data Types */

    typedef  ldp-session-state{
        type enumeration {
            enum non-existent { 
                value 0;
                description
                  "Non-existent state. Transport disconnected.";
            }
            enum initialized { 
                value 1;
                description
                  "Initialized state.";
            }
            enum openrec {
                value 2;
                description
                  "Openrec state. Open to receiving from peer.";
            }
            enum opensent {
                value 3;
                description
                  "Opensent state.";
            }
            enum operational {
                value 4;
                description
                  "Operational state.";
            }
            enum helper-mode {
                value 5;
                description
                  "Graceful-restart helper mode.";
            }
            enum restarting {
                value 6;
                description
                  "Restarting state.";
            }
            enum gr-disabled { 
                value 7;
                description
                  "Graceful-restart disabled.";
            }
            enum unknown {
                value 8;
                description
                  "Unknown state.";
            }
            enum error {
                value 9;
                description
                  "Error state.";
            }
        }
    }

    typedef ldp-gr-state {
        type enumeration {
            enum stale {
                value 0;
                description
                    "Graceful Restart state - Stale.";
            }
            enum fresh {
                value 1;
                description
                    "Graceful Restart state - Fresh.";
            }
        }
    }

    typedef  ldp-label-advertisement-mode{
        type enumeration {
            enum downstream-unsolicited { value 0;    }
            enum downstream-on-demand { value 1;    }
        }
    }

    typedef  ldp-label-retention-mode{
        type enumeration {
            enum liberal { value 0;    }
            enum conservative { value 1;    }
        }
    }

    typedef  ldp-merge-capability{
        type enumeration {
            enum merge-capable { value 0;    }
            enum non-merge-capable { value 1;    }
        }
    }

    typedef  ldp-ipv4-state{
        type enumeration {
            enum disable-ldp { value 0;    }
            enum enable-ldp { value 1;    }
        }
    }

    typedef  ldp-ipv6-state{
        type enumeration {
            enum disable-ldp { value 0;    }
            enum enable-ldp { value 1;    }
        }
    }

    typedef  ldp-igp-sync{
        type enumeration {
            enum igp-sync { value 0;    }
            enum no-igp-sync { value 1;    }
        }
    }

    typedef  ldp-instance{
        type enumeration {
            enum ldp { value 1;    }
        }
    }

    typedef  ldp-debug{
        type bits {
            bit events { position 0;  }
            bit fsm { position 1;  }
            bit hexdump { position 2;  }
            bit dsm { position 3;  }
            bit usm { position 4;  }
            bit tsm { position 5;  }
            bit qos { position 6;  }
            bit nsm { position 7;  }
            bit advertise-labels { position 8;  }
            bit cspf { position 9;  }
            bit vc-usm { position 10;  }
            bit vc-dsm { position 11;  }
            bit graceful-restart { position 12;  }
            bit rib { position 13;  }
            bit ha { position 14;  }
            bit inter-area { position 15;  }
        }
    }

    typedef  ldp-debug-packet{
        type bits {
            bit notification { position 0;  }
            bit hello { position 1;  }
            bit initialization { position 2;  }
            bit keepalive { position 3;  }
            bit address { position 4;  }
            bit label { position 5;  }
        }
    }

    typedef  ldp-failure{
        type enumeration {
            enum restart { value 0;    }
        }
    }

    typedef  ldp-cspf{
        type enumeration {
            enum no-cspf { value 0;    }
            enum cspf { value 1;    }
        }
    }

    typedef  ldp-loose{
        type enumeration {
            enum strict { value 0;    }
            enum loose { value 1;    }
        }
    }

    typedef  ldp-trunk-admin-group{
        type enumeration {
            enum exclude-any { value 0;    }
            enum include-any { value 1;    }
        }
    }

    typedef  ldp-helper-mode{
        type enumeration {
            enum disable { value 0;    }
            enum enable { value 1;    }
        }
    }

    typedef  ldp-label-control-mode{
        type enumeration {
            enum independent { value 0;    }
            enum ordered { value 1;    }
        }
    }


    typedef  mpls-tunnel-direction-type{
        type enumeration {
            enum forward { value 0;    }
            enum reverse { value 1;    }
        }
    }

    typedef  mpls-tpid{
        type enumeration {
            enum 88a8 { value 34984;    }
            enum 9100 { value 37120;    }
        }
    }

    typedef  mpls-vpls-ftn-entry{
        type enumeration {
            enum secondary { value 0;    }
            enum primary { value 1;    }
        }
    }

    typedef  mpls-row-status{
        type enumeration {
            enum active { value 1;    }
            enum not-in-service { value 2;    }
            enum not-ready { value 3;    }
            enum create-go { value 4;    }
            enum create-wait { value 5;    }
            enum destroy { value 6;    }
        }
    }

    typedef  mpls-opcode{
        type enumeration {
            enum swap { value 3;    }
            enum pop { value 4;    }
        }
    }

    typedef  mpls-module{
        type enumeration {
            enum rsvp { value 0;    }
            enum ldp { value 1;    }
            enum bgp { value 4;    }
        }
    }

    typedef  l2vpn-protocol{
        type enumeration {
            enum none { value 1;    }
            enum bgp { value 2;    }
            enum ldp { value 4;    }
            enum ldp-autodiscovery-bgp { value 8;    }
        }
    }

    typedef  mpls-vpls-type{
        type enumeration {
            enum vlan { value 4;    }
            enum ethernet { value 5;    }
        }
    }

    typedef  mpls-vpls-vc-spoke-type{
        type enumeration {
            enum vlan { value 4;    }
            enum ethernet { value 5;    }
        }
    }

    typedef  cml-mpls-admn-status{
        type enumeration {
            enum up { value 1;    }
            enum down { value 2;    }
            enum testing { value 3;    }
        }
    }

    typedef  mpls-opr-status{
        type enumeration {
            enum up { value 1;    }
            enum down { value 2;    }
            enum testing { value 3;    }
            enum dormant { value 4;    }
            enum not-persent { value 5;    }
            enum ll-down { value 6;    }
        }
    }

    typedef  mpls-bfd-flag{
        type enumeration {
            enum configured { value 0;    }
            enum enabled { value 1;    }
            enum disable { value 2;    }
        }
    }

    typedef  mpls-stats-role{
        type enumeration {
            enum ingress { value 0;    }
            enum transit { value 2;    }
        }
    }

    typedef  mpls-stats-owner{
        type enumeration {
            enum ldp { value 0;    }
            enum bgp { value 1;    }
            enum bgp_lu {value 2;  }
            enum sr  { value 3;    }
        }
    }

    typedef  mpls-protocols{
        type enumeration {
            enum ldp {
                 value 0;
                 description
                    "LDP Protocol label-range ";
            }
            enum bgp {
                 value 1;
                 description
                    "BGP Protocol label-range";
            }
            enum default {
                 value 15;
                 description
                    "Default label-range";
            }
            enum rsvp {
                 if-feature rsvp;
                 value 2;
                 description
                    "RSVP protocol label-range";
            }
            enum srgb {
                 value 3;
                 description
                    "SRGB protocol label-range";
            }
            enum srlb {
                 if-feature srlb;
                 value 4;
                 description
                    "SRLB(Adj SID) protocol label-range";
            }
            enum static-vc {
                 if-feature static-vc;
                 value 6;
                 description
                    "Static VC protocol label-range";
            }
            enum static-tunnel {
                 value 7;
                 description
                    "Static tunnel protocol label-range";
            }
        }
    }

    typedef mpls-afi {
        type enumeration {
            enum ipv4 {
                 value 0;
                 description
                    "MPLS address-family IPv4.";
            }
            enum ipv6 {
                 value 1;
                 description
                    "MPLS address-family IPv6.";
            }
            enum srtev4 {
                 value 4;
                 description
                    "MPLS address-family SRTEv4.";
            }
            enum ias-vpnv4 {
                 value 5;
                 description
                    "MPLS address-family IAS VPNv4.";
            }
            enum mplstpv4 {
                 value 6;
                 description
                    "MPLS address-family MPLSTPv4.";
            }
            enum fec128 {
                 value 7;
                 description
                    "MPLS address-family FEC128.";
            }
            enum mspw {
                 value 8;
                 description
                    "MPLS address-family MSPW.";
            }
            enum ifindex {
                 value 9;
                 description
                    "MPLS address-family IF index.";
            }
            enum ias-vpnv6 {
                 value 10;
                 description
                    "MPLS address-family IAS VPNv6.";
            }
            enum rsvptev4 {
                 value 11;
                 description
                    "MPLS address-family RSVPTEv4";
            }
        }
        description
           "MPLS FTN/ILM AFI type.";
    }

  /* OSPF Data Types */

    typedef ospf-link-metric {
      type uint16 {
        range "1 .. 65535";
      }
      description
        "OSPF Link Metric - 16-bit unsigned integer.";
    }

    typedef  ospf-metric-type {
       type enumeration {
           enum type-1 { value 1;    }
           enum type-2 { value 2;    }
       }
   }

   typedef ospf-route-source {
      type enumeration {
         enum static  { 
            description
                "Redistribute static route into OSPF.";
            value 1;     
         }
         enum connected { 
            description
                "Redistribute connected route into OSPF.";
            value 2;     
         }
         enum bgp {
            description
               "Redistribute BGP into OSPF.";
            value 3;
         }
         enum isis {
            description
               "Redistribute ISIS into OSPF.";
            value 4;
         }
      }
   }

  typedef  ospf-auth-type{
       type enumeration {
           enum none { value 0;    }
           enum message-digest { value 2;    }
       }
   }

   typedef  ospf-message-digest-type {
       type enumeration {
           enum md5 { value 1;    }
       }
   }

   typedef  ospf-if-state {
        type enumeration {
            enum ospf-api-status-enabled { value 1;    }
            enum ospf-api-status-disabled { value 2;    }
        }
    }

    typedef  ospf-network-type {
        type enumeration {
            enum point-to-point {
               value 1;
               description
                  "Specify OSPF point-to-point network.";
            }
            enum broadcast {
               value 2;
               description
                  "Specify OSPF broadcast multi-access network.";
            }
        }
    }

    typedef  ospf-prefix-filter{
        type enumeration {
            enum filter-in { value 1;    }
            enum filter-out { value 2;    }
        }
    }

    typedef  ospfv3-prefix-filter{
         description
            "OSPFv3 prefix-filter types";        
         type enumeration {
              enum filter-in { 
                   description
                        "OSPFV3 prefix filter in.";
                   value 1;    
              }
              enum filter-out { 
                   description
                        "OSPFV3 prefix filter out.";
                   value 2;    
              }
         }
    }

    typedef  ospf-range-advertise{
        type enumeration {
            enum not-advertise { value 1;    }
            enum advertise { value 2;    }
        }
    }

   typedef ospf-intf-state-type {
      type enumeration {
         enum down { value 1;    }
         enum loopback { value 2;    }
         enum waiting { value 3;    }
         enum point-to-point { value 4;    }
         enum dr-other { value 5;    }
         enum backup { value 6;    }
         enum designated-router { value 7;    }
      }
   }

   typedef ospf-route-type{
      type enumeration {
        enum unspecified {
           value "0";
           description 
             "Unspecified.";
        }
        enum intra-area {
           value "1";
           description 
             "OSPF intra-area route.";
        }
        enum inter-area {
           value "3";
           description 
             "OSPF inter-area route.";
        }
        enum external {
           value "5";
           description 
             "OSPF External route.";
        }
        enum nssa {
           value "7";
           description 
             "OSPF NSSA external route.";
         }
       }
    }

    typedef ospf-router-link-type {
       type enumeration {
         enum unspecified {
           value "0";
           description 
             "Unspecified.";
         }
         enum point-to-point {
           value "1";
           description
             "Point-to-Point link to Router";
         }
         enum transit-network {
           value "2";
           description
             "Link to transit network identified by
              Designated-Router (DR)";
         }
         enum stub-network {
           value "3";
           description
             "Link to stub network identified by subnet";
         }
         enum virtual {
           value "4";
           description
             "Virtual link across transit area";
         }
       }
       description
         "OSPF Router Link Type.";
   }

   typedef ospf-nbr-state-type {
       type enumeration {
         enum down {
           value "1";
           description
             "Neighbor down state.";
         }
         enum attempt {
           value "2";
           description
             "Neighbor attempt state.";
         }
         enum init {
           value "3";
           description
             "Neighbor init state.";
         }
         enum 2-way {
           value "4";
           description
             "Neighbor 2-Way state.";
         }
         enum exstart {
           value "5";
           description
             "Neighbor exchange start state.";
         }
         enum exchange {
           value "6";
           description
             "Neighbor exchange state.";
         }
         enum loading {
           value "7";
           description
             "Neighbor loading state.";

         }
         enum full {
           value "8";
           description
             "Neighbor full state.";
         }
       }
       description
         "OSPF neighbor state type.";
   }

   typedef ospf-vlink-state-type {
      type enumeration {
        enum down {
          value "1";
          description
            "Vlink is down";
        }
        enum up {
          value "0";
          description
            "Vlink is up";
        }
      }
    }
   // generic types
    typedef string-max-256 {
        type string{
           length 1..256;
        }
    }

    typedef string-max-255 {
        type string{ 
           length 1..255; 
        }
    }

    typedef string-max-680 {
        type string{ 
           length 1..680; 
        }
    }

    typedef ip-prefix {
        type union {
           type inet:ipv4-prefix;
           type inet:ipv6-prefix;
        }
       description
            "The ip-prefix type represents an IP prefix and is IP
             version neutral.  The format of the textual representations
             implies the IP version.";
    }

    // Routing Policy types
    typedef  addpath-all{
        type enumeration {
            enum all { value 4; }
        }
        description
           "Set additional paths value as all";
    }

    typedef  addpath-best{
        type uint8 {
             range "2..3";
        }
        description
           "Set best additional paths as 2 or 3";
    }

    typedef  additional-paths-type{
        type union{
            type addpath-best;
            type addpath-all;
        }
        description
           "Set additional paths as best value[2/3] or all";
    }

    typedef  origin-type{
        type enumeration {
            enum egp { value 1;    }
            enum igp { value 2;    }
            enum incomplete { value 3;    }
        }
        description
           "Route origin eg. IGP or EGP or incomplete.";
    }

    typedef  policy-level-types{
        type enumeration {
            enum level-1 { value 1;   }
            enum level-2 { value 2;   }
            enum level-1-2 { value 3; }
        }
        description
           "ISIS level-type for routing policy";
    }

    typedef  action {
        type enumeration {
            enum deny { value 1; }
            enum permit { value 2; }
        }
        description
           "Action to permit or deny prefix-list, as-path list etc.";
    }

    typedef std-community-type {
            type string {
                pattern '((6553[0-5]|655[0-2]\d|65[0-4]\d{2}|6[0-4]\d{3}|[0-5]?\d{1,3}\d|[1-9]):'
                        + '(6553[0-5]|655[0-2]\d|65[0-4]\d{2}|6[0-4]\d{3}|[0-5]?\d{1,3}\d|[0-9]))';
                length 1..11;
            }
        description
          "Type definition for standard commmunity attributes";
    }

    typedef well-known-community-type {
        type bits {
            bit no-export {
                 position 0;
                 description
                      "do not advertise the prefix to any eBGP neighbors.";
            }
            bit no-advertise {
                 position 1;
                 description
                      "do not advertise the prefix to any BGP neighbors.";
            }
            bit local-AS {
                 position 2;
                 description
                      "do not advertise the prefix outside of the sub-AS (used for BGP confederations).";
            }
            bit internet {
                 position 3;
                 description
                      "advertise the prefix to all BGP neighbors.";
            }
        }
        description
          "Type definition for well-known commmunity attributes";
    }

    typedef prefix-list-mode
    {
        type enumeration {
            enum ipv4 {
            description
                "Prefix set contains IPv4 prefixes only";
            }
            enum ipv6 {
            description
                "Prefix set contains IPv6 prefixes only";
            }

        }
    }

    typedef community-append
    {
        type enumeration {
            enum replace { value 1;   }
            enum append { value 2;   }
        }
    }

    typedef ext-comm-rt {
       type string {
         pattern
           '(0:(6553[0-5]|655[0-2]\d|65[0-4]\d{2}|6[0-4]\d{3}|'
         + '[0-5]?\d{1,3}\d|[1-9]):(6553[0-5]|655[0-2]\d|65[0-4]\d{2}|6[0-4]\d{3}|'
         + '[0-5]?\d{1,3}\d|[1-9]))|'
         + '(1:(((\d|[1-9]\d|1\d{2}|2[0-4]\d|25[0-5])\.){3}(\d|[1-9]\d|'
         + '1\d{2}|2[0-4]\d|25[0-5])):(6553[0-5]|655[0-2]\d|'
         + '65[0-4]\d{2}|6[0-4]\d{3}|[0-5]?\d{1,3}\d|[1-9]))';
       }
       description
         "route target is an AA:NN 8-octet BGP extended community
          RFC4360 and RFC5668, the encoding pattern is defined as:

          0:2-octet-asn:4-octet-number
          1:4-octet-ipv4addr:2-octet-number
          Some valid examples are: 0:100:100, 0:65535:65535 and 1:1.1.1.1:100";

       reference
         "RFC4360: BGP Extended Communities Attribute.
          RFC5668: 4-Octet AS Specific BGP Extended Community.";
    }

    typedef ext-comm-rt-max {
       type string {
           pattern
           '((\s?((0:(6553[0-5]|655[0-2]\d|65[0-4]\d{2}|6[0-4]\d{3}|'
         + '[0-5]?\d{1,3}\d|[1-9]):(429496729[0-5]|42949672[0-8]\d|'
         + '4294967[01]\d{2}|429496[0-6]\d{3}|42949[0-5]\d{4}|'
         + '4294[0-8]\d{5}|429[0-3]\d{6}|42[0-8]\d{7}|4[01]\d{8}|'
         + '[0-3]?\d{1,8}\d|[0-9]))|'
         + '(1:(((\d|[1-9]\d|1\d{2}|2[0-4]\d|25[0-5])\.){3}(\d|[1-9]\d|'
         + '1\d{2}|2[0-4]\d|25[0-5])):(6553[0-5]|655[0-2]\d|'
         + '65[0-4]\d{2}|6[0-4]\d{3}|[0-5]?\d{1,3}\d|[0-9]))|'
         + '(2:(429496729[0-5]|42949672[0-8]\d|4294967[01]\d{2}|'
         + '429496[0-6]\d{3}|42949[0-5]\d{4}|4294[0-8]\d{5}|'
         + '429[0-3]\d{6}|42[0-8]\d{7}|4[01]\d{8}|[0-3]?\d{1,8}\d|[1-9]):'
         + '(6553[0-5]|655[0-2]\d|65[0-4]\d{2}|6[0-4]\d{3}|'
         + '[0-5]?\d{1,3}\d|[0-9])))){1,20})';
         length 1..680;
       }
       description
         "Route target is an AS:NN 8-octet value representing the AS number and the extended community value.
          The encoding pattern is defined as:

          RT-0 is represented as 0:2-octet-asn:4-octet-number
          RT-1 is represented as 1:4-octet-ipv4address:2-octet-number
          RT-2 is represented as 2:4-octet-asn:2-octet-number
          Some valid examples are: 0:100:100, 0:65535:65535, 1:1.1.1.1:100, 2:2107483647:65135";

       reference
         "RFC4360: BGP Extended Communities Attribute
          RFC5668: 4-Octet AS Specific BGP Extended Community";
    }

    typedef large-community-type {
       type string {
          pattern '(\s?((429496729[0-4]|42949672[0-8]\d|4294967[01]\d{2}|429496[0-6]\d{3}|42949[0-5]\d{4}|'
                  + '4294[0-8]\d{5}|429[0-3]\d{6}|42[0-8]\d{7}|4[01]\d{8}|[0-3]?\d{1,8}\d|[1-9])'
                  + '(:(429496729[0-5]|42949672[0-8]\d|4294967[01]\d{2}|429496[0-6]\d{3}|42949[0-5]\d{4}|'
                  + '4294[0-8]\d{5}|429[0-3]\d{6}|42[0-8]\d{7}|4[01]\d{8}|[0-3]?\d{1,8}\d|[0-9])){2})){1,20}';
                length 1..680;
          }
       description
          "Type definition for standard large commmunity attributes";
    }


    typedef pseudowire-mode {
        type enumeration {
           enum 'mesh' {
              description
                 "PW mode type is mesh";
           }
           enum 'spoke' {
              description
                 "PW mode type is spoke";
           }
           enum 'switching' {
              description
                 "PW mode type is switching";
           }
           enum 'tdm-xc' {
              description
                 "PW mode type is tdm crossconnect";
           }
        }

    }

    typedef  l2vpn-protection-type{
        type enumeration {
           enum active { value 0;    }
           enum passive { value 1;    }
        }
    }

    typedef mpls-afi-type {
        type enumeration {
            enum ipv4 { value 1;    }
            enum ipv6 { value 2;    }
        }
    }

    typedef ospf-lsa-source {
        type union {
            type inet:ipv4-address;
            type string;
        }
    }

    typedef ospf-lsa-type {
        type enumeration {
            enum unknown { value 0;    }
            enum router  { value 1;    }
            enum network { value 2;    }
            enum summary { value 3;    }
            enum asbr-summary { value 4;    }
            enum as-external { value 5;    }
            enum multicast { value 6;   }
            enum nssa-external { value 7;    }
            enum external-attribute { value 8;    }
            enum link-opaque { value 9;    }
            enum area-opaque { value 10;    }
            enum as-opaque { value 11;    }
        }
    }

    typedef tunnel-type {
        type enumeration {
            enum static-ingress-corouted     { value 1;    }
            enum static-transit-corouted     { value 2;    }
            enum static-egress-corouted      { value 3;    }  
            enum rsvp-ingress-corouted       { value 4;    }
            enum rsvp-transit-corouted       { value 5;    }
            enum rsvp-egress-corouted        { value 6;    }
            enum sr-policy                   { value 7;    }
            enum rsvp-ingress-unidirectional { value 8;    }
        }
    }

    typedef ldp-igp-sync-holddown {
      description
         "OSPF LDP IGP sync hold down timer value";
      type union{
         type uint32 {
            range "1..69999";
         }

         type enumeration {
            enum none {
               description
                  "No LDP IGP sync hold timer";
               value 0;
            }
            enum infinite {
               description
                  "Infinite LDP IGP sync hold timer";
               value 70000;
            }
         }
      }
   }

   typedef  ospf-rlfa-protection-type {
      description
         "OSPF RLFA protection type enumeration";
      type enumeration {
         enum downstream-protection {
            description
               "RLFA downstream protection";
            value 1;
         }
      }
   }

   typedef  ospfv3-rlfa-protection-type {
      description
         "OSPFV3 RLFA protection type enumeration.";
      type enumeration {
         enum downstream-protection {
            description
               "RLFA downstream protection.";
            value 1;
         }
      }
   }

   typedef sr-status {
     description
       "SR oper/admin status enumeration";
     type enumeration {
       enum Up {
         description
           "oper/admin status is up.";
         value 1;
       }
       enum Down {
         description
           "oper/admin status is down.";
         value 2;
       }
     }
   }

   typedef sr-policy-admin-cfg-type {
     type enumeration {
         enum enable {
           description
             "Specify to enable sr-policy";
         }
         enum disable {
           description
             "Specify to disable sr-policy";
         }
     }
     default "enable";
     description
       "Enum for admin state of an SR policy.";
   }
   
   typedef sr-policy-admin-state {
     type enumeration {
       enum enabled {
         description
           "Specify if policy admin-state is enabled";
       }
       enum disabled {
         description
           "Specify if policy admin-state is disabled";
       }
     }
     description
       "Enum to specify the admin state of an SR Policy.";
   }

   typedef policy-metric-type {
      description
         "Route Map Set  metric-type enumeration.";
       type enumeration {
          enum external {
             description
                 "IS-IS external metric type.";
             value 1;
          }
          enum internal {
             description
                 "IS-IS internal metric type.";
             value 2;
          }
          enum type-1 {
             description
                 "OSPF external type 1 metric.";
             value 3;
          }
          enum type-2 {
             description
                 "OSPF external type 2 metric.";
             value 4;
         }
      }
   }

   typedef policy-route-type {
      description
         "Route Map match route-type enumeration.";
       type enumeration {
          enum type-1 {
             description
                 "OSPF External Type 1 metric.";
             value 1;
          }
           enum type-2 {
              description
                  "OSPF External Type 2 metric.";
              value 2;
          }
       }
   }
   typedef  prefix-list-proto {
      description
         "Prefix list protocol enumeration.";
       type enumeration {
           enum bgp {
               description
                   "Prefix-list protocol type BGP.";
               value 1;
           }
           enum ospf {
               description
                   "Prefix-list protocol type OSPF.";
               value 2;
           }
       }
   }

   typedef ospf-inst-state-type {
       type enumeration {
         enum created {
           value "1";
           description
             "State for creation.";
         }
         enum deleted {
           value "2";
           description
             "State for deletion.";
         }
         enum modified {
           value "3";
           description
             "State for modification.";
         }
      }
   }

   typedef ospf-gr-reason {
       type enumeration {
         enum unknown {
           value "0";
           description
             "Unplanned outages";
         }
         enum restart {
           value "1";
           description
             "Software restart";
         }
         enum upgrade {
           value "2";
           description
             "Software reload/upgrade";
         }
         enum switch-redundant {
           value "3";
           description
             "Switch to redundant control processor";
         }
      }
   }

   typedef isis-inst-state-type {
       type enumeration {
         enum created {
           value "1";
           description
             "State for creation.";
         }
         enum deleted {
           value "2";
           description
             "State for deletion.";
         }
         enum modified {
           value "3";
           description
             "State for modification.";
         }
      }
   }
   typedef mpls-next-hop-type {
      type enumeration {
         enum primary {
            value "1";
            description
               "Primary next-hop";
         }
         enum backup {
            value "2";
            description
               "Backup next-hop";
         }
       }
   }

   typedef bgp-test-afi {
       type enumeration {
         enum ipv4 {
            value 1;
            description
               "BGP IPv4 address family.";
         }
         enum ipv6 {
            value 2;
            description
               "BGP IPv6 address family.";
         }
       }
   }

   typedef bgp-test-safi {
       type enumeration {
         enum unicast {
            value 1;
            description
               "BGP unicast sub-address family.";
         }
       }
   }

   typedef fallback-cfg-type {
     type enumeration {
         enum enable {
           description
             "Specify to enable fallback";
         }
         enum disable {
           description
             "Specify to disable fallback";
         }
     }
     default "enable";
     description
       "Fallback enable is used when the SR policy is down.
        The service will still continue to be up, but
        will fall back to labeled IGP shortest path.";
   }

   typedef fallback-state-type {
     type enumeration {
         enum enabled {
           description
             "Specify if fallback is enabled";
         }
         enum disabled {
           description
             "Specify if fallback is disabled";
         }
     }
     description
       "Fallback enable is used when the SR policy is down.
        The service will still continue to be up, but
        will fall back to labeled IGP shortest path.";
   }

   grouping sr-policy-cfg-grouping {
     container sr-policy {
       leaf color {
          type uint32;
          description
            "Color associated with the SR policy";
       }

       leaf fallback {
         type cn-l3-types:fallback-cfg-type;
         description
           "Fallback enable or disable.";
       }
     }
  }

   grouping sr-policy-oper-grouping {
     container sr-policy {
       leaf color {
          type uint32;
          description
            "Color associated with the SR policy";
       }

       leaf fallback {
         type cn-l3-types:fallback-state-type;
         description
           "Fallback enabled or disabled.";
       }
     }
  }

/* VRF event data type */

   typedef  vrf-event-type {
      description
         "VRF event type enumeration.";
      type enumeration {
         enum vrf-route-mid-threshold {
            value 1;
            description
               "This event is generated when the VRF routes fall below the configured reinstall threshold value";
         }
         enum vrf-route-max-threshold {
            value 2;
            description
               "This event is raised when the VRF routes count exceeds the configured warning threshold value";
         }
         enum vrf-route-max-threshold-clear {
            value 3;
            description
               "This event is raised when the VRF routes count exceeds the configured warning threshold value and then falls below this value";
         }
      }
   }

   typedef vrf-reason-type {
      description
         "A set of enumerated values to indicate the reason for a VRF event.";
      type enumeration {
         enum vrf-route-mid-threshold-exceeded {
            value 1;
            description
               "MPLS L3VPN VRF route mid threshold exceeded";
         }
         enum vrf-route-max-threshold-exceeded {
            value 2;
            description
               "MPLS L3VPN VRF route maximum threshold exceeded";
         }
         enum vrf-route-max-threshold-cleared {
            value 3;
            description
               "MPLS L3VPN VRF route maximum threshold cleared.";
         }
      }
   }

  typedef evpn-evlag-reason-type {
     description
       "A set of enumerated values to indicate the reason for a EVLAG event.";
     type enumeration {
       enum route-update{
         value 1;
         description
           "Ethernet Segment Route update received from peer";
       }
       enum config-change {
         value 2;
         description
           "Ethernet Segment configuration change";
       }
     }
   }

   typedef ethernet-segment-fault-reason-type {
     description
       "A set of enumerated values to indicate the reason for a Ethernet Segment fault event.";
     type enumeration {
       enum up {
         value 1;
         description
           "logical-port is up";
       }
       enum down {
         value 2;
         description
           "logical-port is down";
       }
     }
   }

   typedef transport-type {
      description
         "A set of enumerated values of different MPLS transport types.";
      type enumeration {
         enum ldp {
            value 1;
            description
               "MPLS transport type as LDP";
         }

         enum sr-be {
            value 2;
            description
               "MPLS transport type as SR-BE";
         }

         enum rsvp-te {
            value 3;
            description
               "MPLS transport type as RSVP-TE";
         }
      }
   }

   typedef transport-template-type {
      description
         "A set of enumerated values of different type of transport template.";
      type enumeration {
         enum global {
            value 1;
            description
               "Global type of transport template that applies to
                all services(l2vpn,l3vpn,evpn..etc) on the system";
         }
      }
   }

   typedef transport-template-type-oper {
      description
         "A set of enumerated values of different type of transport template.";
      type enumeration {
         enum global {
            value 1;
            description
               "Global type of transport template that is created by user.";
         }

         enum default {
            value 2;
            description
               "Default type of transport template that is created 
                by default in system.";
         }
      }
   }

   typedef transport-template-status {
      type enumeration {
         enum inactive {
            value 0;
            description
                "Transport template is not operational.";
         }

         enum active {
            value 1;
            description
                "Transport template is operational.";
         }
      }
   }

   typedef label-mode-type {
        type enumeration {
            enum "per-prefix" {
              description
                "Per prefix label.";
            }

            enum "per-vrf" {
              description
                "Per VRF label";
            }
        }
    }

    typedef  ls-prefix-type {
      description
         "BGP link-state prefix type enumeration.";
      type enumeration {
          enum intra-area {
              description
                  "Prefix type intra-area.";
              value 1;
          }
          enum inter-area {
              description
                  "Prefix type inter-area.";
              value 2;
          }
          enum e1 {
              description
                  "Prefix type external 1.";
              value 3;
          }
          enum e2 {
              description
                  "Prefix type external 2.";
              value 4;
          }
          enum nssa1 {
              description
                  "Prefix type NSSA 1.";
              value 5;
          }
          enum nssa2 {
              description
                  "Prefix type NSSA 2.";
              value 6;
          }
      }
   }

   typedef ieeefloat32 {
      type binary {
          length "4";
      }

      description
        "An IEEE 32-bit floating point number. The format of this number
         is of the form:
         1-bit  sign
         8-bit  exponent
         23-bit fraction
         The floating point value is calculated using:
            (-1)**S * 2**(Exponent-127) * (1+Fraction)";
  }   

  typedef mpls-flags-type {
      type bits {
          bit installed { position 0;  }
          bit selected { position 1;  }
          bit stale { position 2;  }
      }
      description
          "Type definition for cross-connect entry flags to distinguish state of forwarding entry";
  }

  typedef sr-sidtype-grouping {
    description
      "Defining types for SRV6 sid.";
    type enumeration {
      enum uncompressed-sid { 
        description
          "SID type as uncompressed SID.";
        value 1;    
      }
      enum u-sid {
        description
          "SID type is micro SID.";
        value 2;  
      }
    }
    default "uncompressed-sid";
  }

  typedef pim-mode-type {
      description
          "Operational modes of the PIM protocol.";
      type enumeration {
          enum "sparse" {
              description
                  "PIM sparse mode.";
          }
          enum "dense" {
              if-feature pim-dm;
              description
                  "PIM dense mode.";
          }

          enum "smdm" {
              if-feature pim-smdm;
              description
                  "PIM sparse and dense modes combined.";
          }
      }
  }

  typedef group-join-state {
      description
          "The group membership state.";
      type enumeration {
          enum "JOINED" {
              description
                  "JOINED state";
          }
          enum "NOT JOINED" {
              description
                  "NOT JOINED state";
          }
      }
  }
   
  typedef pim-downstream-state {
      description
          "The downstream state of S,G,I entry.";
      type enumeration {
          enum no-info {
              description
                  "Initial state of downstream interface or state triggered by Expiry Timer or Prune-Pending Timer";
          }
          enum join {
              description
                  "Join received for the S,G entry on this interface.";
          }
          enum prune-pending {
              description
                  "Prune received, waiting for downstream routers to override the prune.";
          }
      }
  }

  typedef pim-node-role {
      description
          "The role of the next hop node used by the PIM protocol to reach its destinations.";
      type enumeration {
          enum "N" {
               description
                   "New";
          }
          enum "R" {
               description
                   "Next hop to RP";
          }
          enum "S" {
               description
                   "Next hop to source";
          }
          enum "M" {
               description
                   "MSDP peer";
          }
          enum "U" {
               description
                   "Unreachable";
          }
      }
  }

  typedef membership-state {
      description
          "Local membership information for PIM interfaces.";
      type enumeration {
          enum "Include" {
              description
                  "Include state";
          }
          enum "Exclude" {
              description
                  "Exclude state";
          }
          enum "No Info" {
              description
                  "No info state";
          }
      }
  }

  typedef  mroute-event-type {
      description
          "The events occuring with the multicast route.";
      type enumeration {
          enum create { 
              value 0;
              description
                  "This event is raised when the mroute is created.";
          }
          enum delete { 
              value 1;
              description
                  "This event is raised when the mroute is deleted.";
          }
          enum reject { 
              value 2;
              description
                  "This event is raised when the mroute creation was rejected.";
          }
      }
  }
   
  typedef  ospfv3-metric-type {
    description
       "OSPFV3 metric type enumeration.";
    type enumeration {
      enum type-1 { 
        description
            "OSPFV3 metric type 1.";
        value 1;    
      }
      enum type-2 { 
        description
            "OSPFV3 metric type 2.";
        value 2;    
      }
    }
  }

  typedef ospfv3-route-source {
    description
       "OSPFV3 route source type enumeration.";
    type enumeration {
      enum static  { 
        description
          "Redistribute static route into OSPFV3.";
        value 1;     
      }
      enum connected { 
        description
          "Redistribute connected route into OSPFV3.";
        value 2;     
      }
      enum bgp {
        description
          "Redistribute BGP into OSPFV3.";
        value 3;
      }
      enum isis {
        description
          "Redistribute ISIS into OSPFV3.";
        value 4;
      }
    }
  }

  typedef ospfv3-link-metric {
    description
      "OSPFV3 Link Metric - 16-bit unsigned integer.";
    type uint16 {
      range "1 .. 65535";
    }
  }

  typedef  ospfv3-range-advertise{
    description
       "OSPFV3 summary range type enumeration.";
    type enumeration {
      enum not-advertise { 
        description
          "OSPFV3 range not-advertise.";
        value 1;    
      }
      enum advertise { 
        description
          "OSPFV3 range advertise.";
        value 2;    
      }
    }
  }

  typedef ospfv3-intf-state-type {
    description
       "OSPFV3 interface state enumeration.";
    type enumeration {
      enum down { 
        description
          "OSPFV3 interface state down.";
        value 1;    
      }
      enum loopback { 
        description
          "OSPFV3 interface state loopback.";
        value 2;    
      }
      enum waiting { 
        description
          "OSPFV3 interface state waiting.";
        value 3;    
      }
      enum point-to-point { 
        description
          "OSPFV3 interface state point-to-point.";
        value 4;    
      }
      enum dr-other { 
        description
          "OSPFV3 interface state DR-other.";
        value 5;    
      }
      enum backup { 
        description
          "OSPFV3 interface state backup.";
        value 6;    
      }
      enum designated-router { 
        description
          "OSPFV3 interface state designated-router.";
        value 7;    
      }
    }
  }

  typedef ospfv3-lsa-type {
    description
       "OSPFV3 LSA type enumeration.";
    type enumeration {
      enum unknown { 
        description
          "OSPFV3 LSA type unknown.";
        value 0;    
      }
      enum router  { 
        description
          "OSPFV3 LSA type router.";
        value 1;    
      }
      enum network { 
        description
          "OSPFV3 LSA type network.";
        value 2;    
      }
      enum inter-prefix { 
        description
          "OSPFV3 LSA type inter-prefix.";
        value 3;    
      }
      enum inter-router { 
        description
          "OSPFV3 LSA type inter-router.";
        value 4;    
      }
      enum as-external { 
        description
          "OSPFV3 LSA type AS-external.";
        value 5;    
      }
      enum group-member { 
        description
          "OSPFV3 LSA type group-member.";
        value 6;   
      }
      enum nssa { 
        description
          "OSPFV3 LSA type NSSA.";
        value 7;    
      }
      enum link-lsa { 
        description
          "OSPFV3 LSA type link.";
        value 8;    
      }
      enum intra-prefix { 
        description
          "OSPFV3 LSA type intra prefix.";
        value 9;    
      }
      enum area-opaque { 
        description
          "OSPFV3 LSA type area opaque.";
        value 10;    
      }
      enum grace-lsa { 
        description
          "OSPFV3 LSA type grace LSA.";
        value 11;    
      }
    }
  }

  typedef ospfv3-vlink-state-type {
    description
       "OSPFV3 Vlink state type enumeration.";
    type enumeration {
      enum down {
        value "1";
        description
          "Virtual link is down";
      }
      enum up {
        value "0";
        description
          "Virtual link is up";
      }
    }
  }
  
   typedef assoc-types {
    type enumeration {
      enum association-type-srpolicy {
        value 6;
        description
          "Association type as srpolicy.";
      }
    }
  }
  typedef sync-state {
    type enumeration {
      enum pending {
        value 0;
        description
          "The state synchronization has not started.";
      }
      enum ongoing {
        value 1;
        description
          "The state synchronization is ongoing.";
      }
      enum finished {
        value 2;
        description
          "The state synchronization is finished.";
      }
    }
    description
      "State synchronization operational status.";
  }

    typedef evpn-rt5-types {
        type enumeration {
            enum vpnv4 {
                value 1;
                description
                "BGP VPNv4 address family.";
            }
            enum vpnv6 {
                value 2;
                description
                "BGP VPNv6 address family.";
            }
        }
    }

  typedef evpn-route-types {
      description
         "Route types for EVPN address family.";
      type enumeration {
          enum 1 {
            value 1;
            description
                "Ethernet auto-discovery (A-D) route.";
          }
          enum 2-mac-ip {
            value 2;
            description
                "MAC-IP advertisement route.";
          }
          enum 2-mac-only {
            value 3;
            description
                "MAC only advertisement route.";
          }
          enum 3 {
            value 4;
            description
               "Inclusive multicast ethernet tagged route.";
          }
          enum 4 {
            value 5;
            description
                "Ethernet segment route.";
          }
          enum 5 {
            value 6;
            description
                "IP prefix route.";
          }
          enum 6 {
            value 7;
            description
               "Selective multicast ethernet tagged route.";
          }
      }
  }

  typedef aigp-metric-type {
    type enumeration {
      enum replace { value 1; }
      enum increment { value 2; }
    }
  }

  typedef ospf-gr-status {
     description
        "OSPF GR operational status.";
     type enumeration {
        enum in-progress {
           description
              "OSPF GR is in process.";
           value 1;
        }
        enum complete {
           description
              "OSPF GR completed.";
           value 2;
        }
        enum timed-out {
           description
              "Restart timed out.";
           value 3;
        }
        enum topology-changed {
           description
              "Restart aborted due to topology change.";
           value 4;
        }
        enum neighbor-down {
           description
              "neighborship broke due to dead timer expiry.";
           value 5;
        }
        enum error {
           description
              "Failure occured.";
           value 6;
        }
        enum not-applicable {
           description
              "OSPF GR Restart/Helper not in running state.";
           value 7;
        }
     }
  }
}
