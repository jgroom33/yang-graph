module ciena-twamp-light {
  namespace "http://www.ciena.com/ns/yang/ciena-twamp-light";

  prefix "twamp-light";

  import ietf-inet-types {
    prefix inet;
  }
  import ietf-yang-types {
    prefix yang;
  }
  import ciena-twamp-statistics {
    prefix stats;
  }

  organization
    "Ciena Corporation";

  contact
    "Web URL: http://www.ciena.com/
    E-mail:  yang@ciena.com
    Postal:  7035 Ridge Road
             Hanover, Maryland 21076
             U.S.A.
    Phone:   +1 800-921-1144
    Fax:     +1 410-694-5750";

  description 
    "Ciena Corporation TWAMP Light Data Model";
  
  revision "2024-02-09" {
    description
      "Added status deprecated for list historical-statistics";
  }
  revision "2023-03-30" {
    description
      "Change the UDP port range";
  }
  revision "2023-01-24" {
    description
      "Change the minimum interval to 100ms.";

    reference
      "RFC 5357 Appendix I";
  }
  revision "2022-09-27" {
    description
      "Added RPCs for clearing statistics of 
       TWAMP Light Sender and TWAMP Light Reflector.";
  }
  revision "2022-09-08" {
    description
      "Initial version";

    reference
      "RFC 5357 Appendix I";
  }

  typedef twamp-name {
    type string {
      length "1..45";
      pattern '[0-9a-zA-Z\-_.]*';
    }
    description
      "String uniquely identifying the twamp light test session
       on the node.";
  }

  typedef light-session-reflector-mode {
    type enumeration {
      enum stateful {
        description
          "When the session reflector is stateful,
           i.e. is aware of TWAMP-Test session state.";
      }
      enum stateless {
        description
          "When the session reflector is stateless,
           i.e. is not aware of the state of
           TWAMP-Test session.";
      }
    }
    description 
      "Indicates whether or not the light session reflector
       can keep state for individual light test sessions.";
  }

  typedef light-session-reflector-dscp-mode {
    type enumeration {
      enum copy-received-value {
        description
          "Use DSCP value copied from received
           TWAMP test packet of the test session.";
      }
      enum use-configured-value {
        description
          "Use DSCP value configured for this
           test session on the light session reflector.";
      }
    }
    description
      "DSCP handling mode by light session reflector.";
  }

  typedef light-fill-mode {
    type enumeration {
      enum random {
        description
          "Fill packet padding with random pattern.";
      }
      enum zero {
        description
          "Fill packet padding with 0.";
      }
      enum one {
        description
          "Fill packet padding with 1.";
      }
    }
    description 
      "Fill pattern for packet-padding.";
  }
  typedef light-current-state {
    type enumeration {
      enum active {
        description
          "Test session is active";
      }
      enum idle {
        description
          "Test session is idle";
      }
    }
    description
      "State of the light test session at the sender";
  }

  grouping light-session-id {
    description
      "Unique ID of the test-session is represented by this 4-tuple
      src IP, dest IP, src UDP port, dest UDP port.
      These must be configured at creation and cannot be modified.";

  leaf sender-ip {
    type inet:ip-address;
    mandatory true;
    description 
      "Sender IP address";
  }
  leaf sender-udp-port {
    type inet:port-number {
      range "1000..65535";
    }
    description
      "Sender UDP port number";
  }
  leaf reflector-ip {
    type inet:ip-address;
    mandatory true;
    description 
      "Reflector IP address";
    }
  leaf reflector-udp-port {
    type inet:port-number{
      range "862 | 1000..65535";
    }
    default 862;
    description 
      "Reflector UDP port number";
    }
  }


  /* Configuration Data */

  container twamp-light {
    description
      "Top level container for TWAMP Light configuration";

    leaf admin-state {
      type boolean;
      default false;
      description 
        "True indicates that TWAMP is running in light-mode.
         Only config from this YANG model is in use and any config
         in the ietf-twamp.yang standard model is ignored.
         False indicates we are running standards based TWAMP and
         all other configuration from this YANG model is ignored. 
         In standards based mode, the configuration in 
         ietf-twamp.yang is used";
    }

    container light-session-sender {
      description 
        "TWAMP Light Session-Sender container";

      list light-test-session {
        key "name";
        unique "sender-ip sender-udp-port reflector-ip"
        +"  reflector-udp-port";
        unique "sender-ip sender-udp-port";
        description
          "TWAMP Light configured test session objects";

        leaf name {
          type twamp-name;
          description
            "A unique name used as a key to identify this individual
             TWAMP test session on the light-session-sender device";
        }

        uses light-session-id;

        must "sender-ip !=reflector-ip" {
          error-message "Sender and Reflector IPs should not be equal";
        }

        leaf test-packet-dscp {
          type inet:dscp;
          default 0;
          description
             "DSCP value to be set in the test packet
              generated by the light-session-sender.";
        }

        leaf number-of-packets {
          type union {
            type yang:counter32 {
              range 0..4294967294;
            }
            type enumeration {
              enum for-fixed-duration {
                description
                  "Indicates that the test session shall
                   run for a fixed duration, as specifed 
                   in the duration leaf.";
              }
            }
          }
          default 300;
          description
             "The overall number of TWAMP-Test (UDP) packets to be
              transmitted by the light-Session-Sender 
              for this test session.
              If forever, then the test session shall continue to run 
              for the time specified in duration.";
        }
  
        leaf duration {
          when "../number-of-packets = 'for-fixed-duration'";
          type uint32;
          units seconds;
          default 900;
          description
            "Time test session would run for in seconds. How many 
             packets this is depends on the packet transmission
             interval.  This value is only used if the number of
             packets for the session is set to for-fixed-duration.";
        }

        leaf interval  {
          type uint32 {
            range 100..4294967294;
          }
          units milliseconds;
          default 1000;
          description
            "Time interval between transmission of two
            consecutive test packets in the test session in
            miliseconds";
        }

        leaf repeat {
          type union {
            type uint32 {
              range 0..4294967294;
            }
            type enumeration {
              enum forever {
                description
                  "Indicates that the test session SHALL be
                   repeated *forever* using the information in
                   repeat-interval parameter, and SHALL NOT
                   decrement the value.";
              }
            }
          }
          default 0;
          description
            "This value determines if the TWAMP-Test session must
             be repeated. When a test session has completed, the
             repeat parameter is checked.
             The default value of 0 indicates that the session
             MUST NOT be repeated.
             If the repeat value is 1 through 4,294,967,294
             then the test session SHALL be repeated using the
             information in repeat-interval parameter";
        }

        leaf repeat-interval {
          when "../repeat != '0'";
          type uint32;
          units seconds;
          default 0;
          description
            "This parameter determines the timing of repeated
             TWAMP-Test sessions when repeat is more than 0.";
        }

        leaf packet-length { 
          type uint32 {
            range 64..2000;
          }
          default 128;
          description
            "The length of the TWAMP-Test (UDP) packets
             generated by the Light-Session-Sender, in bytes.
             This includes the IP header.
             For IPv4 test sessions the minimum length is 64.
             For IPv6 test sessions the minimum length is 84.";
        }

        leaf fill-mode {
          type light-fill-mode;
          default zero;
          description
            "Indicates whether the padding added to the TWAMP-Test 
             (UDP) packets for this light test session will contain 
             pseudo-random numbers, or whether it should consist of 
             all zeroes, or all 1s.";
        }

        leaf test-session-reflector-mode {
          type light-session-reflector-mode;
          default "stateful";
          description
            "The mode of light session reflector for this 
             light test session.";
        }

        leaf round-trip-threshold {
          type uint32;
          units microseconds;
          description
            "Threshold for round-trip delay time in microseconds.";
        }

        leaf round-trip-pdv-threshold {
          type uint32;
          units microseconds;
          description
            "Threshold for round-trip PDV time in microseconds.";
        }

        leaf one-way-out-threshold {
          type uint32;
          units microseconds;
          description
            "Threshold for one-way-out delay time in microseconds.";
        }

        leaf one-way-out-pdv-threshold {
          type uint32;
          units microseconds;
          description
            "Threshold for one-way-out PDV time in microseconds.";
        }

        leaf reflector-processing-threshold {
          type uint32;
          units microseconds;
          description
            "Threshold for reflector processing delay time in microseconds.";
        }

        leaf reflector-processing-pdv-threshold {
          type uint32;
          units microseconds;
          description
            "Threshold for reflector processing PDV time in microseconds.";
        }

        leaf one-way-back-threshold {
          type uint32;
          units microseconds;
          description
            "Threshold for one-way-back delay time in microseconds.";
        }

        leaf one-way-back-pdv-threshold {
          type uint32;
          units microseconds;
          description
            "Threshold for one-way-back PDV time in microseconds.";
        }

        leaf vrf-name {
          type twamp-name;
          description
            "Name used to specify the VRF name where the sender IP address belongs.";
        }
      }
    }

    container light-session-reflector {
      description
        "TWAMP Light session reflector container";

      leaf light-session-reflector-mode {
        type light-session-reflector-mode;
        default stateful;
        description
          "The mode of the light session reflector.";
      }

      list light-test-session {
        key "name";
        unique "sender-ip sender-udp-port reflector-ip"
        +" reflector-udp-port";
        unique "reflector-ip reflector-udp-port";
        description
          "TWAMP Light configured test session objects";

        leaf name {
          type twamp-name;
          description
            "A unique name used as a key to identify this individual
             TWAMP test session on the light-session-reflector";
        }

        uses light-session-id;

        must "sender-ip !=reflector-ip" {
          error-message "Sender and Reflector IPs should not be equal";
        }

        leaf admin-state {
          type boolean;
          default false;
          description 
            "True indicates that the TWAMP reflector is willing
             to reflect packets for this session. 
             False indicates that packets will not be reflected.";
        }

        leaf dscp-handling-mode {
          type light-session-reflector-dscp-mode;
          default copy-received-value;
          description
            "light session reflector handling of DSCP:
             - use value copied from received TWAMP-Test packet;
             - use value explicitly configured";
        }

        leaf dscp-value {
          when "../dscp-handling-mode = 'use-configured-value'";
          type inet:dscp;
          default 0;
          description
            "DSCP value to be set in the reflected packet
             if dscp-handling-mode is set to use-configured-value.";
        }

        leaf vrf-name {
          type twamp-name;
          description
            "Name used to specify the VRF name where the sender IP address belongs.";
        }
      }
    }
  }


  /* Operational Data */

  container twamp-light-state {

    config "false";

    description
      "Top level container for TWAMP Light operational data";

    container light-session-sender-state {
      description
        "Light-Session-Sender state data";

      list test-session-state {
        key "name";
        description
          "TWAMP Light-session-sender operational test session data";

        leaf name {
          type twamp-name;
          description
            "A unique name used as a key to identify this individual
             TWAMP test session on the light-session-sender device";
        }

        leaf current-state {
          type light-current-state;
          description
            "State of the light test session at the sender";
        }

        container current-statistics {
          description
            "Statistics for active light test sessions";
    
          leaf last-sent-seq {
            type uint32;
            description 
              "Sequence number of the most recent test packet
               sent by the light-sender for this test session";
          }
          leaf last-rcv-seq {
            type uint32;
            description 
              "Sequence Number of the most recent test packet
               received by the light sender for this test session";
          }

          uses stats:base-counters;

          container round-trip-statistics {
            description
              "Round trip measurements for the session";

            uses stats:base-measurements;
          }

          container one-way-out-statistics {
            description
              "one-way-out measurements for the session";

            uses stats:base-measurements;
          }

          container reflector-processing-statistics {
            description
              "reflector processing measurements for the session";

            uses stats:base-measurements;
          }

          container one-way-back-statistics {
            description
              "one-way-back measurements for the session";

            uses stats:base-measurements;
          }
        }

        list historical-statistics {
          key "index";
          status deprecated;
          description
            "Statistics for previous iterations of this 
             light test session";

          leaf index {
            type uint8 {
              range "1..96";
            }
            description
              "Index for a completed iteration of this 
               light test session.";
          }
         
          leaf end-time {
            type yang:date-and-time;
            description
              "The time that the light test session ended";
          }

          leaf test-packet-dscp {
            type inet:dscp;
            description
              "The DSCP value used in the generated test packets
               during this iteration of the light test session.";
          }

          leaf number-of-packets {
            type yang:counter32;
            description 
              "number of packets configured for this iteration of 
               the light test session";
          }

          leaf interval  {
            type uint32;
            units microseconds;
            description
              "Time interval between transmission of two
               consecutive test packets used for this iteration of 
               the light test session."; 
          }

          leaf packet-length {
            type uint32 {
              range 64..2000;
            }
            description
              "The length of the TWAMP-Test (UDP) packets
               used in this iteration of the light test session.";
          }

          leaf fill-mode {
            type light-fill-mode;
            default zero;
            description
              "The fill-mode used in this iteration of the
               light test session.";
          }

          leaf test-session-reflector-mode {
            type light-session-reflector-mode;
            description
              "The mode of light session reflector for this iteration 
               of the light test session.";
          }

          uses stats:base-counters;

          container round-trip-statistics {
            description
              "Round trip measurements for the session";

            uses stats:base-measurements;
          }

          container one-way-out-statistics {
            description
              "one-way-out measurements for the session";

            uses stats:base-measurements;
          }

          container reflector-processing-statistics {
            description
              "reflector processing measurements for the session";

            uses stats:base-measurements;
          }

          container one-way-back-statistics {
            description
              "one-way-back measurements for the session";

            uses stats:base-measurements;
          }
        }
      }
    }

    container light-session-reflector-state {
      description
        "TWAMP light session reflector operational data";

      list test-session-state {
        key "name";

        description
          "TWAMP Light-session-sender operational test session data";

        leaf name {
          type twamp-name;
          description
            "A unique name used as a key to identify this individual
             TWAMP test session on the light-session-sender device";
        }

        container current-statistics {
          description
            "Reflector statistics for light test session";

          leaf sent-packets {
            type yang:counter32;
            description 
              "Packets sent";
          }
          leaf rcv-packets {
            type yang:counter32;
            description 
              "Packets received";
          }

          leaf last-sent-seq {
            type uint32;
            description 
              "Sequence number of the most recent test packet
               sent by the light-reflecfor this test session";
          }
          leaf last-rcv-seq {
            type uint32;
            description 
              "Sender Sequence Number in the most recent test packet
               received by the light reflector for this test session";
          }
        }
      }
    }
  }

  rpc twamp-sender-start {
    description
      "start the configured light sender test session";
    input {
      leaf name {
        type twamp-name;
        mandatory true;
        description
          "The light test session to be started";
      }
    }
    output {
      leaf status {
        type string;
        description
          "Status of the start session operation.";
      }
    }
  }

  rpc twamp-sender-stop {
    description
      "stop the light sender test session";
    input {
      leaf name {
        type twamp-name;
        mandatory true;
        description
          "The session to be stopped";
      }
    }
    output {
      leaf status {
        type string;
        description
          "Status of the stop session operation.";
      }
    }
  }

  rpc twamp-light-sender-clear-statistics {
    description
      "TWAMP light sender clear statistics";
    input {
      leaf name {
        type twamp-name;
        description
          "A unique name used as a key to identify this individual
           TWAMP test session on the light-session-sender device";
      }
    }
    output{
      leaf status {
        type string;
        description
          "Status of the clear TWAMP sender statistics operation";
      }
    }
  }

  rpc twamp-light-reflector-clear-statistics {
    description
      "TWAMP light reflector clear statistics";
      input {
        leaf name {
          type twamp-name;
          description
            "A unique name used as a key to identify this individual
             TWAMP test session on the light-session-reflector device";
        }
      }
      output{
        leaf status {
          type string;
          description
            "Status of the clear TWAMP reflector statistics operation";
        }
      }
   }
}
