module ciena-openconfig-system-deviation {
  namespace "http://www.ciena.com/ns/yang/ciena-openconfig-system-dev";
  prefix "oc-sys-dev";

  import openconfig-system { 
    prefix oc-sys;
    revision-date 2017-07-06;
  }
  import ietf-inet-types { prefix inet; } 
  import ciena-openconfig-aaa-types { prefix cn-oc-aaa-types; } 
  import ciena-openconfig-system { prefix ciena-oc-sys; }
  import yumaworks-extensions { prefix "ywx"; }

  organization
    "Ciena Corporation";
  
  contact
    "Web URL: http://www.ciena.com/
     E-mail:  yang@ciena.com
     Postal:  7035 Ridge Road
              Hanover, Maryland 21076
              U.S.A.
     Phone:   +1 800-921-1144
     Fax:     +1 410-694-5750";
      
  description
    "This YANG module defines Ciena's deviations from the openconfig-system model.

      Copyright (c) 2017 Ciena Corporation.  All rights 
      reserved.

      All information contained herein is, and remains
      the property of Ciena Corporation. Dissemination of this 
      information or reproduction of this material is strictly 
      forbidden unless prior written permission is obtained from 
      Ciena Corporation.";

  revision 2023-12-04 {
    description
      "Added deviation for hostname to modify maximum length from 253 to 63.
       Changed pattern to allow only alpha-numeric, _, - and . characters";
    reference
      "";
  }

  revision 2023-09-13 {
    description
      "Added deviation for username to modify type and description.
      Adding MAX Users creation limit as 100";
    reference
      "";
  }

  revision 2023-03-22 {
    description
      "Removing deviation on login-banner";
    reference
      "";
  }

  revision 2021-02-12 {
    description
      "Add deviation for RADIUS/TACACS config for source-address";
    reference
      "";
  }

  revision 2020-09-29 {
    description
      "Add deviation for openconfig-system state components";
    reference
      "";
  }

  revision 2020-08-14 {
    description
      "Add deviation for openconfig-aaa user role";
    reference
      "";
  }

  revision 2019-08-08 {
    description 
      "Add support for welcome banner";
    reference
      "";
  }
   
  revision 2018-05-30 {
    description 
      "Removing deviation on tacacs/config/secret-key with YANG length substatement";
    reference
      "";
  }

  revision 2017-08-29 {
    description 
      "Initial version";
    reference
      "RFC 6020: YANG - A Data Modeling Language for
       the Network Configuration Protocol (NETCONF).
       No specific reference; standard not available.";
  }

  //
  // Configuration deviations
  //

  deviation /oc-sys:system/oc-sys:config/oc-sys:hostname {
    deviate replace {
      type string {
        length "1..63";
        pattern '[a-zA-Z0-9_.-]+';
      }
    }
  }

  deviation /oc-sys:system/oc-sys:config/oc-sys:domain-name {
    deviate not-supported;
  }

  deviation /oc-sys:system/oc-sys:state/oc-sys:hostname {
    deviate not-supported;
  }

  deviation /oc-sys:system/oc-sys:state/oc-sys:domain-name {
    deviate not-supported;
  }

  deviation /oc-sys:system/oc-sys:state/oc-sys:boot-time {
    deviate not-supported;
  }

  deviation /oc-sys:system/oc-sys:clock {
    deviate not-supported;
  }

  deviation /oc-sys:system/oc-sys:dns {
    deviate not-supported;
  }

  deviation /oc-sys:system/oc-sys:ntp {
    deviate not-supported;
  }

  deviation /oc-sys:system/oc-sys:ssh-server/oc-sys:config/oc-sys:enable {
    deviate not-supported;
  }

  deviation /oc-sys:system/oc-sys:ssh-server/oc-sys:config/oc-sys:protocol-version {
    deviate not-supported;
  }

  deviation /oc-sys:system/oc-sys:ssh-server/oc-sys:config/oc-sys:timeout {
    deviate replace {
      type uint16 {
        range "0 | 60..max";
      }
    }
  }

  deviation /oc-sys:system/oc-sys:ssh-server/oc-sys:config/oc-sys:rate-limit {
    deviate not-supported;
  }

  deviation /oc-sys:system/oc-sys:ssh-server/oc-sys:config/oc-sys:session-limit {
    deviate not-supported;
  }

  deviation /oc-sys:system/oc-sys:ssh-server/oc-sys:state/oc-sys:enable {
    deviate not-supported;
  }

  deviation /oc-sys:system/oc-sys:ssh-server/oc-sys:state/oc-sys:protocol-version {
    deviate not-supported;
  }

  deviation /oc-sys:system/oc-sys:ssh-server/oc-sys:state/oc-sys:timeout {
    deviate not-supported; 
  }

  deviation /oc-sys:system/oc-sys:ssh-server/oc-sys:state/oc-sys:rate-limit {
    deviate not-supported;
  }

  deviation /oc-sys:system/oc-sys:ssh-server/oc-sys:state/oc-sys:session-limit {
    deviate not-supported;
  }

  deviation /oc-sys:system/oc-sys:telnet-server {
    deviate not-supported;
  }

  deviation /oc-sys:system/oc-sys:logging {
    deviate not-supported;
  }

  deviation /oc-sys:system/oc-sys:aaa/oc-sys:authentication/oc-sys:config/oc-sys:authentication-method {
    deviate replace {
      type string;
    }
  }

  deviation /oc-sys:system/oc-sys:aaa/oc-sys:authentication/oc-sys:state/oc-sys:authentication-method {
    deviate not-supported;
  }

  deviation /oc-sys:system/oc-sys:aaa/oc-sys:authentication/oc-sys:admin-user {
    deviate not-supported;
  }

  deviation /oc-sys:system/oc-sys:aaa/oc-sys:authentication/oc-sys:users/oc-sys:user/oc-sys:config/oc-sys:username {
    deviate replace {
      type string {
        length "1..32";
        pattern '[a-zA-Z0-9_.@][a-zA-Z0-9_.@-]*';
      }
    }
    deviate add {
      ywx:help
        "Assigned username for this user. Supported characters are a-z, A-Z, 0-9, '.', '-', '@' and  '_'
         Username cannot begin with '-' character";
    }
  }

  deviation /oc-sys:system/oc-sys:aaa/oc-sys:authentication/oc-sys:users/oc-sys:user/oc-sys:config/oc-sys:password {
    deviate not-supported;
  }

  deviation /oc-sys:system/oc-sys:aaa/oc-sys:authentication/oc-sys:users/oc-sys:user/oc-sys:config/oc-sys:role {                          
    deviate replace {                                                                                                                     
      type union {                                                                                                                        
        type string;                                                                                                                      
        type identityref {                                                                                                                
          base cn-oc-aaa-types:CIENA_SYSTEM_DEFINED_ROLES;                                                                                
        }                                                                                                                                 
      }                                                                                                                                   
    }                                                                                                                                     
  }                                                                                                                                       
 
  deviation /oc-sys:system/oc-sys:aaa/oc-sys:authentication/oc-sys:users/oc-sys:user/oc-sys:config/oc-sys:ssh-key {
    deviate not-supported;
  }

  deviation /oc-sys:system/oc-sys:aaa/oc-sys:authentication/oc-sys:users/oc-sys:user/oc-sys:state/oc-sys:ssh-key {
    deviate not-supported;
  }

  deviation /oc-sys:system/oc-sys:aaa/oc-sys:authorization {
    deviate not-supported;
  }

  deviation /oc-sys:system/oc-sys:aaa/oc-sys:accounting/oc-sys:config/oc-sys:accounting-method {
    deviate replace {
      type string;
    }
  }

  deviation /oc-sys:system/oc-sys:aaa/oc-sys:accounting/oc-sys:state {
    deviate not-supported; 
  }

  deviation /oc-sys:system/oc-sys:aaa/oc-sys:accounting/oc-sys:events/oc-sys:event/oc-sys:state {
    deviate not-supported; 
  }

  deviation /oc-sys:system/oc-sys:aaa/oc-sys:server-groups/oc-sys:server-group/oc-sys:state {
    deviate not-supported; 
  }

  // type inet:host will take hostname as well as ipv4/ipv6
  deviation /oc-sys:system/oc-sys:aaa/oc-sys:server-groups/oc-sys:server-group/oc-sys:servers/oc-sys:server/oc-sys:config/oc-sys:address {
    deviate replace {
      type inet:host;
    }
  }

  // deviate for default timeout value
  deviation /oc-sys:system/oc-sys:aaa/oc-sys:server-groups/oc-sys:server-group/oc-sys:servers/oc-sys:server/oc-sys:config/oc-sys:timeout {
    deviate add {
      default 5;
    }
  }

  deviation /oc-sys:system/oc-sys:aaa/oc-sys:server-groups/oc-sys:server-group/oc-sys:servers/oc-sys:server/oc-sys:state/oc-sys:name {
    deviate not-supported; 
  }

  deviation /oc-sys:system/oc-sys:aaa/oc-sys:server-groups/oc-sys:server-group/oc-sys:servers/oc-sys:server/oc-sys:state/oc-sys:address {
    deviate not-supported; 
  }

  deviation /oc-sys:system/oc-sys:aaa/oc-sys:server-groups/oc-sys:server-group/oc-sys:servers/oc-sys:server/oc-sys:state/oc-sys:timeout {
    deviate not-supported; 
  }

  deviation /oc-sys:system/oc-sys:aaa/oc-sys:server-groups/oc-sys:server-group/oc-sys:servers/oc-sys:server/oc-sys:tacacs/oc-sys:state {
    deviate not-supported; 
  }

  deviation /oc-sys:system/oc-sys:aaa/oc-sys:server-groups/oc-sys:server-group/oc-sys:servers/oc-sys:server/oc-sys:tacacs/oc-sys:config/oc-sys:source-address {
    deviate not-supported;
  }

  deviation /oc-sys:system/oc-sys:aaa/oc-sys:server-groups/oc-sys:server-group/oc-sys:servers/oc-sys:server/oc-sys:radius/oc-sys:config/oc-sys:retransmit-attempts {
    deviate replace {
      type uint8 {
        range "0..3";
      }
    }
    deviate add {
      default 3;
    }
  }

  deviation /oc-sys:system/oc-sys:aaa/oc-sys:server-groups/oc-sys:server-group/oc-sys:servers/oc-sys:server/oc-sys:radius/oc-sys:config/oc-sys:source-address {
    deviate not-supported;
  }

  deviation /oc-sys:system/oc-sys:aaa/oc-sys:server-groups/oc-sys:server-group/oc-sys:servers/oc-sys:server/oc-sys:radius/oc-sys:state/oc-sys:auth-port {
    deviate not-supported;
  }

  deviation /oc-sys:system/oc-sys:aaa/oc-sys:server-groups/oc-sys:server-group/oc-sys:servers/oc-sys:server/oc-sys:radius/oc-sys:state/oc-sys:acct-port {
    deviate not-supported;
  }

  deviation /oc-sys:system/oc-sys:aaa/oc-sys:server-groups/oc-sys:server-group/oc-sys:servers/oc-sys:server/oc-sys:radius/oc-sys:state/oc-sys:secret-key {
    deviate not-supported;
  }

  deviation /oc-sys:system/oc-sys:aaa/oc-sys:server-groups/oc-sys:server-group/oc-sys:servers/oc-sys:server/oc-sys:radius/oc-sys:state/oc-sys:source-address {
    deviate not-supported;
  }

  deviation /oc-sys:system/oc-sys:aaa/oc-sys:server-groups/oc-sys:server-group/oc-sys:servers/oc-sys:server/oc-sys:radius/oc-sys:state/oc-sys:retransmit-attempts {
    deviate not-supported;
  }

  deviation /oc-sys:system/oc-sys:aaa/oc-sys:server-groups/oc-sys:server-group/oc-sys:servers/oc-sys:server/oc-sys:radius/oc-sys:state/oc-sys:counters/oc-sys:access-accepts {
    deviate not-supported;
  }

  deviation /oc-sys:system/oc-sys:aaa/oc-sys:server-groups/oc-sys:server-group/oc-sys:servers/oc-sys:server/oc-sys:radius/oc-sys:state/oc-sys:counters/oc-sys:access-rejects {
    deviate not-supported;
  }

  deviation /oc-sys:system/oc-sys:aaa/oc-sys:server-groups/oc-sys:server-group/oc-sys:servers/oc-sys:server/oc-sys:radius/oc-sys:state/oc-sys:counters/oc-sys:timeout-access-requests {
    deviate not-supported;
  }

  deviation /oc-sys:system/oc-sys:memory {
    deviate not-supported;
  }

  deviation /oc-sys:system/oc-sys:processes {
    deviate not-supported;
  }

  deviation /ciena-oc-sys:ssh-user-pubkey-install/ciena-oc-sys:input/ciena-oc-sys:tls-service-profile {
    deviate not-supported;
  }

  deviation /oc-sys:system/oc-sys:aaa/oc-sys:authentication/oc-sys:users/oc-sys:user {
    deviate add {
      max-elements 100;
    }
  }
}
