module ciena-twamp-statistics {
  namespace "http://www.ciena.com/tls/yang/ciena-twamp-statistics";
  prefix "ciena-twamp-statistics";

  import ietf-yang-types {
    prefix yang;
  }

  organization
    "Ciena Corporation";

  contact
    "Web URL: http://www.ciena.com/
    E-mail:  yang@ciena.com
    Postal:  7035 Ridge Road
             Hanover, Maryland 21076
             U.S.A.
    Phone:   +1 800-921-1144
    Fax:     +1 410-694-5750";

  description
    "Ciena Corporation TWAMP Light Data Model";

  revision "2024-02-09" {
    description
      "Added status deprecated for leaf p95-percentile, p999-percentile 
       in module ciena-twamp-statistics";
  }
  revision "2021-09-27" {
    description
      "Added more attributes of TWAMP Light statistics 
       to be populated";
  }
  revision "2021-03-01" {
    description
      "Initial version";

    reference
      "RFC 5357 Appendix I";
  }

  grouping base-counters {
    description
      "Session sender per test-session packet counters.
       Some counters may not be supported when running in light stateless mode.
       Some platforms may support only a sub-set of these statistics.";

    leaf sent-packets {
      type yang:counter32;
      description
        "Packets sent";
    }
    leaf rcv-packets {
      type yang:counter32;
      description
        "Packets received";
    }
    leaf duplicate-packets {
      type yang:counter32;
      description
        "Duplicate packets received";
    }
    leaf out-of-order-packets {
      type yang:counter32;
      description
        "Out of order packets received";
    }
    leaf round-trip-packet-loss {
      type yang:counter32;
      description
        "Packet loss - round trip";
    }
    leaf round-trip-packet-loss-ratio {
      type yang:counter32;
      description
        "Packet loss ratio - round trip";
    }
    leaf one-way-packet-loss {
      type yang:counter32;
      description
        "Packet loss - one way";
    }
    leaf one-way-packet-loss-ratio {
      type yang:counter32;
      description
        "Packet loss ratio - one way";
    }
  }

  grouping base-measurements {
    description
      "Session sender per test session group of measurements.";
       
    leaf min-value {
      type yang:gauge32;
      units microseconds;
      description
        "Minimum value recorded for this measurement in microseconds";
    }
    leaf max-value {
      type yang:gauge32;
      units microseconds;
      description
        "Maximum value recorded for this measurement in microseconds";
    }
    leaf mean-value {
      type yang:gauge32;
      units microseconds;
      description
        "Mean value recorded for this measurement in microseconds";
    }
    leaf pdv-min {
      type yang:gauge32;
      units microseconds;
      description
        "Minimum packet delay variation value recorded for this measurement in microseconds";
    }
    leaf pdv-max {
      type yang:gauge32;
      units microseconds;
      description
        "Maximum packet delay variation value recorded for this measurement in microseconds";
    }
    leaf pdv-mean {
      type yang:gauge32;
      units microseconds;
      description
        "Mean packet delay variation value recorded for this measurement in microseconds";
    }
    leaf p95-percentile {
      type yang:gauge32;
      units microseconds;
      status deprecated;
      description
        "Time under which 95% of all packet measurement values fall";
    }
    leaf p999-percentile {
      type yang:gauge32;
      units microseconds;
      status deprecated;
      description
        "Time under which 99.9% of all packet measurement values fall";
    }
    leaf number-threshold-exceeded {
      type yang:gauge32;
      description
        "Number of packets above the threshold";
    }
    leaf number-threshold-pdv-exceeded {
      type yang:gauge32;
      description
        "Number of packets above the PDV threshold";
    }
  }
}
