module ciena-ospf {
   namespace   "http://ciena.com/ns/yang/ciena-ospf";
   prefix "ospf";

   import ietf-inet-types {
      prefix "inet";
   }

   import yuma-ncx {
      prefix "ncx";
   }

   import openconfig-interfaces {
      prefix "oc-if";
   }

   import ciena-routing-policy {
      prefix "rt-pol";
   }

   import ciena-bfd-types {
      prefix "bfd-types";
   }

   import ietf-routing-types {
      prefix "rt-types";
   }

   import ciena-l3-types {
      prefix cn-l3-types;
   }

   import ietf-yang-types {
      prefix yang;
   }

   import ciena-types {
       prefix ciena-types;
   }

   import ciena-isis {
      prefix "isis";
   }
   organization
      "Ciena Corporation";

   contact
      "Web URL: http://www.ciena.com/
      E-mail:  yang@ciena.com
      Postal:  7035 Ridge Road
      Hanover, Maryland 21076
      U.S.A.
      Phone:   +1 800-921-1144
      Fax:     +1 410-694-5750";

   description
      "This YANG module defines Ciena's IPv4 Open Shortest Path First (ospf) protocol

      Copyright (c) 2019-2022  Ciena Corporation.  All rights
      reserved.

      All information and intellectual property contained in this
      YANG module (Specification) is, and remains the property
      of Ciena Corporation. Ciena retains all title and ownership
      in the Specification, including any revisions.

      Ciena grants all interested parties that access the
      Specification with the intent to use or distribute (you) a
      non-exclusive, no-cost license to use and distribute
      unmodified copies of the Specification solely in connection
      with the management of Ciena products sold by or on
      behalf of Ciena, provided this copyright notice and license
      appear on all copies. Ciena may rescind or modify this
      license at any time.

      This Specification is supplied as is, and Ciena makes no
      warranty, either express or implied, as to the use, operation,
      condition, or performance of the Specification. You agree
      that Ciena has no liability for your use of the Specification.";

   revision "2024-01-15" {
      description
         "Added default value for nssa translator role.
          Added condition for vlink hello and dead interval.
          Updated description for leaf instance under redistribution.";
   }

   revision "2023-06-27" {
      description
         "Added support for graceful restart state attributes.";
   }

   revision "2023-06-01" {
      description
         "Added support for OSPF GR Restart/Helper mode feature.
          Added support for default-information-originate for OSPF normal areas.
          Added support to show link lsdb summary and detail at interface level.
          Added duplicate OSPF router-id indication in the network to notification.
          Added support for Secondary IP related params in interface state.
          Added support to clear ospf neighbor.
          Changed the default value of Restart mode in GR.";
   }


   revision "2023-04-12" {
      description
         "Added support for syslog of Area mismatch between Primary and secondary network addresses.";
   }

   revision "2022-07-12" {
      description
         "Added support for OSPF stub and NSSA area.
          Added support for ospf summary-adress for external routes
          Added translator-role parameter in show ospf area for OSPFv2 NSSA ABR";
   }

   revision "2021-10-27" {
      description
         "Added ISIS multi instance support for ospf redistribute.
          Changed the microloop-avoidance rib-update-delay range minimum value to 1 from 0.";
   }


   revision "2021-10-04" {
      description
         "Added OSPF GR Helper Feature";
   }

   revision "2021-06-25" {
      description
         "Added mtu size parameter on OSPF interface.
          Added Operational status of BFD on OSPF interface.
          Added status of OSPF interface.
          Added neighbors count on particular OSPF interface.";
   }

   revision "2021-03-26" {
      description
         "Added ABR and ASBR support in OSPF instance.
          Increased the ospf authentication password length.
          Added operational-metric leaf for LDP-OSPF sync";
   }

   revision "2020-08-26" {
      description
         "Added neighbour state change notification.
          Added OSPF instance state change notification.
          Added OSPF micro-loop avoidance state parameters";
   }

   revision "2020-02-06" {
      description
         "Including OSPF LDP FRR, TI-LFA, SR extensions
          Added changes for OSPF Virtual link feture
          Added changes for OSPF ldp igp sync operation data
          Updated OSPF LSDB Hierarchy
          Added changes for OSPF ldp igp sync operation data.
          Added Changes for Ospf Virtual link feture.
          Including OSPF LDP FRR, TI-LFA, SR extensions.
          Incorporating Route Map support into OSPF.
          Added OSPF micro-loop avoidance parameters.";
   }

   revision "2019-10-08" {
      description
         "Initial version of ciena-ospf config, state and rpc yang model";
   }

   feature bfd {
      description
         "Support for BFD detection of OSPF neighbor reachability.";
      reference "RFC 5880: Bidirectional Forwarding Detection (BFD)
         RFC 5881: Bidirectional Forwarding Detection
         (BFD) for IPv4 and IPv6 (Single Hop)";
   }

   feature router-id {
      description
         "Set Router-ID per instance explicitly.";
   }

   identity area-type {
      description
         "Base identity for OSPF area type.";
   }

   identity normal-area {

      base area-type;
      description
         "OSPF normal area.";
   }

   grouping instance-config {
      description
         "OSPF instance config state.";

      leaf router-id {
         if-feature router-id;
         type rt-types:router-id;
         description
            "Defined in RFC 2328. A 32-bit number
            that uniquely identifies the router.";
      }

      leaf spf-min-delay  {
         type  uint32 {
            range "1..600000";
         }
         default "500";
         units milliseconds;
         description
            "The minimum SPF delay time in milliseconds: 500 milliseconds.";
      }

      leaf spf-max-delay  {
         type  uint32 {
            range "1..600000";
         }
         default "5000";
         units milliseconds;
         description
            "The maximum SPF hold delay time in milliseconds: 50000
            milliseconds (50 seconds)";
      }

      leaf admin-distance  {
         type  uint32 {
            range "1..255";
         }
         description
            "OSPF administrative distance";
      }

      container default-information-originate {
         description
            "Create a default route into an OSPF routing domain.";

         leaf enable {
             description
                "Enable/Disable advertise default route";
             type boolean;
             default "false";
         }

         container always {
            description
               "Always advertise default route";

            leaf enable {
             description
                "Enable/Disable advertise default route";
             type boolean;
             default "false";
            }
            leaf metric {
               type uint32 {
                  range "0..16777214";
               }
               default "10";
               description
                  "Sets the OSPF metric used in creating the default route";
            }
            leaf metric-type {
               type cn-l3-types:ospf-metric-type;
               default "type-2";
               description
                  "External link type associated with the default route advertised into the OSPF routing domain";
            }
         }
         leaf metric {
            type uint32 {
               range "0..16777214";
            }
            default "10";
            description
               "Sets the OSPF metric used in creating the default route";
        }
        leaf metric-type {
            type cn-l3-types:ospf-metric-type;
            default "type-2";
            description
               "External link type associated with the default route advertised into the OSPF routing domain";
         }
      }

      list redistribute {
         key "protocol";
         description
            "Redistribute routes to external process";

         leaf protocol {
            type cn-l3-types:ospf-route-source;
            description
               "Redistibute protocol name";
         }

         leaf metric-type {
            type cn-l3-types:ospf-metric-type;
            description
               "Metric type";
         }

         leaf metric {
            type  uint32 {
               range "0..16777214";
            }
            default "20";
            description
               "Metric value";
         }

         leaf policy {
            type leafref {
               path "/rt-pol:routing-policy/rt-pol:policies/rt-pol:policy/rt-pol:name";
            }
            description
               "Name of the routemap to apply the filter to.";
         }

         list instance {
            when "../protocol= 'isis'";
            key "tag";
            description
               "ISIS instance when redistribution protocol is ISIS";
            leaf tag {
               type leafref {
                  path "/isis:isis/isis:instance/isis:tag";
               }
               description
                  "Tag should be instance of ISIS";
            }

            leaf metric-type {
               type cn-l3-types:ospf-metric-type;
               description
                  "Metric type";
             }

            leaf metric {
               type  uint32 {
                  range "0..16777214";
               }
               default "20";
               description
                  "Metric value";
            }

            leaf policy {
               type leafref {
                  path "/rt-pol:routing-policy/rt-pol:policies/rt-pol:policy/rt-pol:name";
               }
               description
                  "Name of the routemap to apply the filter to.";
            }
         }

      }

      container fast-reroute {
         description
            "Configurations for OSPF LFA fast reroute";
         container lfa {
            description
               "OSPF LFA fast reroute";
            leaf per-prefix-enable {
               type boolean;
               default "false";
               description
                  "Enables/disables LFA FRR";
            } 
         }
      }

      container graceful-restart {
         description
            "OSPF graceful restart capabilities.";

         leaf helper-enable {
            type boolean;
            default "true";
            description
               "Enable/disable graceful restart helper mode (enabled by default).";
         }
         leaf helper-grace-period {
            type uint16 {
               range "1..1800";
            }
            units seconds;
            default "200";
            description
               "OSPF GR Helper Grace Period in seconds (1-1800) should be greater than Restart grace period";
        }
        leaf restart-capable {
            type boolean;
            default "false";
            description
               "Enable/disable graceful restart capability (disable by default).";
         }
         leaf restart-grace-period {
            type uint16 {
               range "1..1800";
            }
            units seconds;
            default "120";
            description
               "OSPF GR Restart Grace Period in seconds (1-1800)";
        }
      }
   }

   grouping interface-common-config {
      description
         "Common configuration for all types of interfaces,
         including virtual links and sham links.";

      leaf hello-interval {
         type uint16 {
            range "1..65535";
         }
         units seconds;
         default "10";
         description
            "Interval between hello packets (seconds). It must
            be the same for all routers on the same network.
            Different networks, implementations, and deployments
            will use different hello-intervals. A sample value
            for a LAN network would be 10 seconds.";
         reference "RFC 2328: OSPF Version 2, Appendix C.3";
      }

      leaf dead-interval {
         type uint16 {
            range "1..65535";
         }
         units seconds;
         must "../dead-interval > ../hello-interval" {
            error-message "The dead interval must be "
               + "larger than the hello interval";
            description
               "The value must be greater than the 'hello-interval'.";
         }
         default "40";
         description
            "Interval after which a neighbor is declared down
            (seconds) if hello packets are not received. It is

            typically 3 or 4 times the hello-interval. A typical
            value for LAN networks is 40 seconds.";
         reference "RFC 2328: OSPF Version 2, Appendix C.3";
      }

      leaf retransmit-interval {
         type uint16 {
            range "1..1800";
         }
         units seconds;
         default "5";
         description
            "Interval between retransmitting unacknowledged Link
            State Advertisements (LSAs) (seconds). This should
            be well over the round-trip transmit delay for
            any two routers on the network. A sample value
            would be 5 seconds.";

         reference "RFC 2328: OSPF Version 2, Appendix C.3";
      }

      leaf transmit-delay {
         type uint16 {
            range "1..3600";
         }
         units seconds;
         default "1";
         description
            "Estimated time needed to transmit Link State Update
            (LSU) packets on the interface (seconds). LSAs have
            their age incremented by this amount when advertised
            on the interface. A sample value would be 1 second.";
         reference "RFC 2328: OSPF Version 2, Appendix C.3";
      }

      leaf disable {
         type boolean;
         default false;
         description
            "Disable OSPF protocol on the interface.";
      }

      leaf metric {
         type cn-l3-types:ospf-link-metric;
         description
            "Interface cost.";
      }

      leaf lfa-candidate-enable {
         type boolean;
         description
            "Enable/disable the interface from being used as the next hop in a repair path";
         default "true";
      }

      container ldp-igp-sync {
         presence "Configures LDP/IGP Sync parameters";
         description
            "Enables IGP/LDP synchronization";

         leaf hold-down {
            type cn-l3-types:ldp-igp-sync-holddown;
            mandatory true;
            description
               "Hold-down timer for the OSPF ldp-igp synchronization configuration \n range: [1-69999]/none/infinite";
         }
      }
   }

   grouping interface-config {
      description 
         "Configuration for real interfaces.";

      leaf type {
         type enumeration {
            enum "broadcast" {
               description
                  "Specify OSPF broadcast multi-access network.";
            }
            enum "point-to-point" {
               description
                  "Specify OSPF point-to-point network.";
            }
         }
         default "broadcast";
         description
            "Interface type.";
      }

      leaf passive {
         type boolean;
         default "false";
         description
            "Enable/Disable passive interface - a passive interface's
            prefix will be advertised but no neighbor adjacencies
            will be formed on the interface.";
      }
      list authentication  {
         key "id";
         max-elements 1;
         description
            "OSPF message-digest-key (MD5) related operations";
         leaf id  {
            type  uint32{
               range "1..255";
            }
            description
               "Key ID";
         }

         leaf password {
            type  string{
               length "1..16";
            }
            mandatory true;
            ncx:password;
            description
               "MD5 Authentiation key (password)";
         }
      }

      leaf priority {
         type uint8 {
            range "0..255";
         }
         default "1";
         description
            "Configure OSPF router priority. On multi-access network
            this value is for Designated Router (DR) election. The
            priority is ignored on other interface types. A router
            with a higher priority will be preferred in the election
            and a value of 0 indicates the router is not eligible to
            become Designated Router or Backup Designated Router
            (BDR).";
      }

      container bfd {
         if-feature bfd;
         description
            "BFD Client Configuration.";
         uses bfd-types:client-cfg-parms;
         reference "RFC YYYY: YANG Data Model for Bidirectional
            Forwarding Detection (BFD). Please replace YYYY with
            published RFC number for draft-ietf-bfd-yang.";
      }

      leaf mtu  {
         type  uint16 {
            range "576..65535";
         }
         description
            "Set the ospf packet MTU size. By default, ospf uses the
            interface MTU size";
      }

      uses interface-common-config;
   }

   grouping srlr {
      description
         "Grouping for SR label range configuration.";
      leaf lower-bound {
         type uint32 {
            range "16000..1048575";
         }
         description
            "Lower value in the block.";
      }
      leaf upper-bound {
         type uint32 {
            range 16000..1048575;
         }
         description
            "Upper value in the block.";
      }
   }

   grouping srgb-cfg {
      description
         "Grouping for SR global block configuration";
      list srgb {
         key "lower-bound upper-bound";
         max-elements 1;
         ordered-by user;
         description
            "List of global blocks to be advertised.";
         uses srlr;
      }
   }

   grouping area-common-config {
      container fast-reroute {
         description
            "Configurations for OSPF remote LFA fast reroute";
         container remote-lfa {
            description
               "OSPF remote LFA fast reroute";
            leaf enable {
               type boolean;
               default "false";
               description
                  "Enables/disables remote LFA FRR. Must be enabled with instance-level LFA configuration.";
            }

            leaf tunnel-cost  {
               type uint32 {
                  range "1..16777214";
               }
               default "60";
               description
                  "Maximum cost of the repair tunnel.";
            }

            list protection {
               key "protection-type";
               description
                  "Protection provided to the repair tunnel";

               leaf protection-type {
                  type cn-l3-types:ospf-rlfa-protection-type;
                  description
                     "The protection type";
               }
               leaf enable  {
                  type boolean;
                  default "false";
                  description
                     "Enable/disable the protection type";
               }
            }
         }
         container ti-lfa {
            description
               "OSPF TI LFA fast reroute";
            leaf enable {
               type boolean;
               default "false";
               description
                  "Enables/disables TI-LFA FRR, Must be enabled with instance-level LFA configuration";
            } 
         }

      }
   }

   container ospf {
      description
         "OSPF protocol Instance";
      list instance {
         key "tag";
         max-elements 1;
            description
               "OSPF structure";
         leaf tag {
            type uint32 {
               range "0..65535";
            }
            description
               "OSPF instance ID";
         }
         uses instance-config;


         container interfaces {
            description
               "All interfaces.";
            list interface {
               key "name";
               description
                  "List of OSPF interfaces.";
               leaf name {
                  type leafref {
                     path "/oc-if:interfaces/oc-if:interface/oc-if:name";
                  }
                  description
                     "Interface name reference.";
               }
               uses interface-config;

            }
         }

         container areas {
            description
               "All areas.";
            list area {
               key "id";
               max-elements 16;
               description
                  "List of OSPF areas";
               leaf id {
                  type yang:dotted-quad;
                  description
                     "Area ID";
               }

               list network {
                  key "prefix";
                  description
                     "OSPF network";
                  leaf prefix {
                     type inet:ipv4-prefix;
                     description
                        "Network prefix and length";
                  }
               }

               list prefix-list {
                  key "prefix-name";
                  description
                     "Name of the prefix list";
                  leaf prefix-name  {
                     type leafref {
                        path "/rt-pol:routing-policy/rt-pol:prefix-lists/rt-pol:prefix-list/rt-pol:name";
                     }
                     description
                        "Refers to prefix list name";
                  }
                  leaf prefixType  {
                     type  cn-l3-types:ospf-prefix-filter;
                     description
                        "Filter type ( filter-in | filter-out)";
                  }
               }

               list range {
                  key "prefix";
                  description
                     "Summarize routes matching address/mask
                     (Area Border Routers (ABRs) only)";
                  leaf prefix  {
                     type  inet:ipv4-prefix; // We can also use ip-prefix for v4 and v6.
                     description
                        "The network prefix";
                  }
                  leaf range-advertise  {
                     type  cn-l3-types:ospf-range-advertise;
                     default "advertise";
                     description
                        "Advertise or not-advertise";
                  }
               }
               list virtual-link {
                 key "peer-id";
                 description
                   "Virtual link ID(IP addr) associated with neighbor";
                 leaf peer-id {
                   type rt-types:router-id;
                   description
                      "The Virtual Link ID associated with neighbor";
                 }
                 leaf vlink-dead-interval  {
                   type uint32 {
                     range "1..65535";
                   }
                   units seconds;
                   must "../vlink-dead-interval > ../vlink-hello-interval" {
                      error-message "The vlink dead interval must be "
                         + "larger than the vlink hello interval";
                      description
                         "The value must be greater than the 'vlink-hello-interval'.";
                   }
                   default "40";
                   description
                     "Vlink Dead interval (in seconds) for router detection time";
                 }
                 leaf vlink-hello-interval {
                   type uint32 {
                     range "1..65535";
                   }
                   units seconds;
                   default "10";
                   description
                     "Vlink Hello interval (in seconds)";
                 }
                 leaf vlink-retransmit-interval {
                   type uint32 {
                     range "1..1800";
                   }
                   units seconds;
                   default "5";
                   description
                     "Vlink LSA retransmit interval (in seconds)";
                 }
                 leaf vlink-transmit-delay {
                   type uint32 {
                     range "1..3600";
                   }
                   units seconds;
                   default "1";
                   description
                     "Vlink LSA transmission delay (in seconds)";
                 }
                 container bfd {
                   if-feature bfd;
                   description
                      "Enable BFD for virtual link.";
                   uses bfd-types:client-cfg-parms;
                 }
               }

               container type {
                  description
                     "Configure type of area as stub or nssa area";

                  container stub {
                     description
                        "Configure stub area";

                     leaf set {
                        description
                           "Set/Unset the stub area. Set should be true to enable functionality";
                        type boolean;
                        default "false";
                     }

                     leaf no-summary {
                        description
                           "Do not inject inter-area routes into stub";
                        type boolean;
                        default "false";
                     }
                 }

                 container nssa {
                    description
                       "Configure the NSSA area";

                    leaf set {
                       description
                          "Set/Unset the NSSA area. Set should be true to enable functionality";
                       type boolean;
                       default "false";
                    }

                    container  default-information-originate {
                       description
                          "Originate type 7 default LSA into NSSA area";

                       leaf metric-type {
                          type cn-l3-types:ospf-metric-type;
                          description
                             "OSPF metric type for NSSA default routes";
                       }

                       leaf metric {
                          type  uint32 {
                             range "0..16777214";
                          }
                          description
                             "OSPF metric for NSSA default route";
                       }
                    }

                    leaf no-summary {
                       description
                          "Do not send summary LSA into NSSA area";
                       type boolean;
                       default "false";
                    }

                    leaf no-redistribution {
                       description
                          "No redistribution into this NSSA area";
                       type boolean;
                       default "false";
                    }

                    leaf translator-role {
                       description
                          "NSSA-ABR translator role";

                       type enumeration {
                          enum "always" {
                             description
                                "Always translate LSAs";
                          }

                          enum "candidate" {
                             description
                                "Candidate for translator role";
                          }

                          enum "never" {
                             description
                                "Do not translate LSAs";
                          }
                       }
                       default "candidate";
                    }
                 }
               }
               uses area-common-config;
            }
         }

         container segment-routing {
            description
               "Attribute to enable MPLS-based segment routing for an ISIS or OSPF process";
            leaf enabled {
               type boolean;
               default "false";
               description
                  "Enable MPLS Segment Routing";
            }
            uses srgb-cfg;
         }
 
         container microloop-avoidance { 
            description
               "OSPF microloop avoidance configuration.";
            leaf enable {
               type boolean;
               default "false";
               description
                  "Enable/disable microloop avoidance for protected prefixes.";
            }    
 
            leaf rib-update-delay {
               type uint32 {
                  range "1..2147483647";
               }    
               default "5000";
               units milliseconds;
               description
                  "Set route download delay for microloop avoidance on local interfaces.";
            }    
         }

         list summary-address {
            key "prefix";

            description
               "Summary address for external routes. address/mask";

            leaf prefix {
               type inet:ipv4-prefix;
               description
                  "The network prefix";
            }

            leaf address-advertise {
               type cn-l3-types:ospf-range-advertise;
               default "advertise";
               description
                  "Advertise or not-advertise";
            }

            leaf tag {
               type uint32 {
                  range "0..4294967295";
               }
               description
                  "Tag for summary address";
            }
         }
      }
   }

   grouping neighbors-state-grouping {
      leaf area-id  {
         type yang:dotted-quad;
         description
            "Area ID";
      }

      list neighbor-state {
         key "router-id";
         description
            "OSPF neighbor state";
         leaf router-id {
            type rt-types:router-id;
            description
               "Neighbor router ID";
         }

         leaf state-type {
            type string {
               length "0..255";
            }
            description
               "Neighbor state type";
         }

         leaf neighbor-event-count  {
            type  yang:counter32;
            description
               "The number of times this neighbor has changed
               state or an error has occurred. Discontinuities in the
               value of this counter can occur when the OSPF neighbor
               is re-initialized.";
         }

         leaf neighbor-retrans-qlen  {
            type  uint32;
            description
               "The current length of the retransmission queue.";
         }

         leaf lsdb-count {
            type  yang:counter32;
            description
               "Link state Database Count";
         }

         leaf ls-request-count {
            type  yang:counter32;
            description
               "Link State request count";
         }

         leaf ls-retransmit-count {
            type  yang:counter32;
            description
               "Link State retransmission count";
         }

         leaf neighbor-up-time {
            type  string {
               length "0..255";
            }
            description
               "The length of time in seconds the neighbor has been in
               the full adjacency state";
         }

         leaf dr-router-id {
            type rt-types:router-id;
            description
               "Neighbor's Designated Router (DR) Router ID.";
         }

         leaf bdr-router-id {
            type rt-types:router-id;
            description
               "The Backup Designated Router (BDR) Router ID.";
         }

         leaf dead-timer  {
            type  string {
               length "0..255";
            }
            description
               "This timer tracks the remaining time before
               the neighbor is declared dead.";
         }

         leaf priority  {
            type  uint32;
            description
               "Configured OSPF router priority. On multi-access network
               this value is for Designated Router (DR) election. The
               priority is ignored on other interface types. A router
               with a higher priority will be preferred in the election
               and a value of 0 indicates the router is not eligible to
               become Designated Router or Backup Designated Router
               (BDR).";
         }
      }

   }

   grouping pdu-statistics-grouping {

      leaf total-sent {
         type uint32;
         description
            "Total number of packets sent.";
      }

      leaf total-received {
         type uint32;
         description
            "Total number of packets received.";
      }


      leaf hello-sent {
         type uint32;
         description
            "Hello's sent.";
      }

      leaf hello-received {
         type uint32;
         description
            "Hello's received.";
      }

      leaf dd-sent {
         type uint32;
         description
            "Total number of database description packets sent.";
      }

      leaf dd-received {
         type uint32;
         description
            "Total number of database description packets received.";
      }

      leaf ls-request-sent {
         type uint32;
         description
            "Total number of LS requests sent.";
      }

      leaf ls-request-received {
         type uint32;
         description
            "Total number of LS requests received.";
      }

      leaf ls-update-sent {
         type uint32;
         description
            "Total number of LS updates sent.";
      }

      leaf ls-update-received {
         type uint32;
         description
            "Total number of LS updates received.";
      }

      leaf ls-ack-sent {
         type uint32;
         description
            "Total number of LS acknowledgements sent.";
      }

      leaf ls-ack-received {
         type uint32;
         description
            "Total number of LS acknowledgements received.";
      }

      leaf error-packet-tx-count{
         type uint32;
         description
            "Number of packets not transmitted due to error.";
      }

      leaf error-packet-rx-count{
         type uint32;
         description
            "Number of incoming packets with error.";
      }

   }

   grouping interface-state-grouping {
      list interface-state {
         key "name";
         description
            "OSPF interface related operations";
         leaf name  {
            type  string {
               length "0..255";
            }
            description
               "Interface name";
         }

         leaf state {
            type  cn-l3-types:ospf-intf-state-type;
            description
               "Interface state";
         }

         leaf events  {
            type  uint32;
            description
               "The number of times this interface has changed its
               state or an error has occurred. Discontinuities in the
               value of this counter can occur when the OSPF interface
               is re-initialized.";
         }

         leaf lsa-count  {
            type  yang:counter32;
            description
               "The number of link-scope LSAs";
         }

         leaf lsa-cksum-sum  {
            type  uint32;
            description
               "The modulo 2**32 sum of the LSA checksums
               for link-scope LSAs. The value should be treated as
               unsigned when comparing two sums of checksums. While
               differing checksums indicate a different combination
               of LSAs, equivalent checksums don't guarantee that the
               LSAs are the same given that multiple combinations of
               LSAs can result in the same checksum.";
         }

         leaf dr-router-id {
            type rt-types:router-id;
            description
               "Neighbor's Designated Router (DR) Router ID.";
         }

         leaf dr-ip-addr {
            type inet:ip-address;
            description
               "The Designated Router (DR) IP address.";
         }

         leaf bdr-router-id {
            type rt-types:router-id;
            description
               "The Backup Designated Router (BDR) Router ID.";
         }

         leaf ldp-igp-sync-status {
            type string;
            description
               "Status of ldp-igp-sync (Configured or Not Configured).";
         }

         leaf remaining-hold-down-time{
            type uint32;
            units milliseconds;
            description
               "Time in milliseconds before LDP notifies OSPF to advertise original cost.";
         }

         leaf bdr-ip-addr {
            type inet:ip-address;
            description
               "The Backup Designated Router (BDR) IP Address.";
         }
 
         leaf interface-ip-addr {
            type inet:ip-address;
            description
               "The IP Address configured on this OSPF interface.";
         }

         list secondary-ip-address {
            key "secondary-ip";
            description 
               "The list of configured secondary IP addresses on the OSPF interface."; 

            leaf secondary-ip {
               type inet:ip-address;
               description
                  "The secondary IP address on the interface.";
            }
         }

         leaf operational-metric {
            type cn-l3-types:ospf-link-metric;
            description
               "Interface operational cost with respect to LDP-OSPF sync";
         }

         uses pdu-statistics-grouping;

         uses neighbors-state-grouping;

         leaf mtu  {
            type  uint16;
            description
               "OSPF packet MTU size.";
         }

         leaf bfd-state {
            type ciena-types:state;
            description
               "Operational status of BFD on OSPF interface.";
         }

         leaf status {
            type ciena-types:up-down-state;
            description
               "Interface operational status(up/down)";
         }

         leaf neighbors-count {
            type uint16;
            description
               "Neighbors count on the interface";
         }

         leaf secondary-addr-count {
            type uint16;
            description
               "Number of Secondary IP addresses associated with this OSPF interface";
         }

         container lsdb-summary-state
         {
            uses lsdb-interface-summary-grouping;
         }

         container lsdb-detail-state
         {
            uses lsdb-interface-detail-grouping;
         }
      }
   }

   grouping ospf-route-grouping {
      list route-state {
         key "prefix";
         config false;
         description
            "OSPF IPv4 route-table";
         leaf prefix  {
            type inet:ipv4-prefix;
            description
               "Destination prefix of the route";
         }

         leaf type  {
            type  string;
            description
               "Path type attribute";
         }

         list next-hop {
            key "neighbor-ip-addr";
            config false;
            description
               "OSPF IPv4 route next hop";
            leaf neighbor-ip-addr {
               type inet:ipv4-address;
               description
                  "IP address of the neighbor";
            }

            leaf outgoing-interface  {
               type string;
               description
                  "Name of the outgoing interface";
            }

            leaf area-id  {
               type yang:dotted-quad;
               description
                  "Area Id in quad-dotted notation";
            }

            leaf area-transit  {
               type boolean;
               description
                  "Transit area";
            }

            leaf path-cost  {
               type uint32;
               description
                  "Path cost of the route";
            }

            leaf ext-type-cost  {
               type uint32;
               description
                  "Path cost of the External route";
            }
         }
      }
   }

   grouping lsdb-area-summary-grouping {
      list lsdb-area-entry-summary {
         key "lsa-type lsa-id adv-router";
         config false;
         description
            "Summary of LSAs in Area Level LSDB ";

         uses lsa-header;

         leaf do-not-age  {
            type boolean;
            description
               "If true, LSA shall not be removed from the LSDB";
         }

         leaf link-count  {
            type uint32;
            description
               "The number of attached links";
         }

      }
   }

   grouping lsdb-instance-summary-grouping {
      list lsdb-instance-entry-summary {
         key "lsa-type lsa-id adv-router";
         config false;
         description
            "Summary of LSAs in Instance Level LSDB";

         uses lsa-header;

         leaf do-not-age  {
            type boolean;
            description
               "If true, LSA shall not be removed from the LSDB";
         }

         leaf link-count  {
            type uint32;
            description
               "The number of attached links";
         }
      }
   }

   grouping lsdb-interface-summary-grouping {
      list lsdb-interface-entry-summary {
         key "lsa-type lsa-id adv-router";
         config false;
         description
            "Summary of LSAs at Interface Level LSDB";

         uses lsa-header;

         leaf opaque-id  {
            type uint32;
            description
               "Opaque ID";
         }
         leaf opaque-type  {
            type uint8;
            description
               "Opaque Type";
         }
      }
   }

   grouping lsa-header {
       description
          "Common LSA for OSPFv2 and OSPFv3";

       leaf lsa-type {
         type cn-l3-types:ospf-lsa-type;
         description 
            "LSA type";
       }

       leaf lsa-id {
         type yang:dotted-quad;
         description 
            "Link-State ID.";
       }

       leaf adv-router {
         type rt-types:router-id;
         description
            "LSA advertising router.";
       }

       leaf ls-age {
         type uint16;
         description 
            "LSA age.";
       }

       leaf seq-num {
         type uint32;
         description
            "LSA sequence number.";
       }

       leaf checksum {
         type string;
         description 
            "LSA checksum.";
       }

   }

   grouping lsa-header-detail {

      leaf length {
         type uint16;
         description 
           "LSA length including the header.";
      }
       
      leaf options {
         type string;
         description 
            "The Options field enables OSPF routers to support 
             (or not support) optional capabilities, and to
             communicate their capability level to other OSPF routers";
      }

   }

   grouping lsdb-area-detail-grouping {

       list lsdb-area-entry-detail {
         key "lsa-type lsa-id adv-router";
         config false;
         description
             "List OSPF LSAs.";
         
          uses lsa-header;
          uses lsa-header-detail;

          container opaque-lsa {
             leaf opaque-type {
                type uint8;
                description
                   "Opaque type.";
             }

             leaf opaque-id {
                type uint32;
                description 
                   "Opaque ID.";
             }

             container extended-prefix-opaque {
               description 
                  "All extended prefix TLVs in the LSA.";
               list extended-prefix-tlv {
                  key "prefix";
                  description 
                     "Extended prefix TLV.";
                  leaf prefix {
                     type inet:ipv4-prefix;
                     description 
                        "Address prefix.";
                  }

                  leaf route-type {
                     type cn-l3-types:ospf-route-type;
                     description 
                        "Route type.";
                  }

                  leaf flags {
                     type string;
                     description
                        "Extended prefix TLV flags list. This list will
                         contain identities for the prefix flags that
                         are set in the extended prefix flags.
 
                         A: Attach Flag. Set when Area Border Router (ABR)
                            generating an OSPFv2 Extended Prefix TLV for an inter-area
                            prefix that is locally connected or attached in another
                            connected area.

                         N: Node Flag. Set when the prefix identifies the advertising router,
                            i.e., the prefix is a host prefix advertising a globally reachable
                            address typically associated with a loopback address. The advertising 
                            router MAY choose to not set this flag even when the above conditions are met.";
                  }

                  uses prefix-sid-sub-tlvs;
               }
             }

             container extended-link-opaque {
               description 
                  "All extended link TLVs in the LSA.";
  
               list extended-link-tlv {
                  key "link-id";

                  description 
                     "Extended link TLV.";
                  uses ospfv2-router-link;

                  container adj-sid-sub-tlvs {        
                     description 
                        "Adjacency SID optional sub-TLVs.";        
                     list adj-sid-sub-tlv {          
                        description 
                           "List of Adjacency SID sub-TLVs.";
                        key "sid"; 
                     
                        leaf sid {           
                           type uint32;            
                           description 
                              "Segment Identifier (SID) index/label.";          
                        }  

                        leaf flags {            
                           type string;                 
                           description 
                              "Adj-sid sub-tlv flags.

                               B-Flag:  Backup Flag.  If set, the Adj-SID refers to an
                                        adjacency that is eligible for protection (e.g., using IP
                                        Fast Reroute or MPLS-FRR (MPLS-Fast Reroute) as described
                                        in Section 2.1 of [RFC8402].

                               V-Flag:  Value/Index Flag.  If set, then the Adj-SID carries
                                        an absolute value.  If not set, then the Adj-SID carries
                                        an index.

                               L-Flag:  Local/Global Flag.  If set, then the value/index
                                        carried by the Adj-SID has local significance.  If not
                                        set, then the value/index carried by this sub-TLV has
                                        global significance.
                     
                               S-Flag.  Set Flag. When set, the S-Flag indicates that the Adj-SID 
                                        refers to a set of adjacencies (and therefore MAY be assigned
                                        to other adjacencies as well).";
                        }

                        leaf mt-id {            
                           type uint8;            
                           description 
                              "Multi-topology ID.";          
                        }
          
                        leaf weight {            
                           type uint8;            
                           description 
                              "Weight used for load-balancing.";          
                        }       
                     }     
                  }     
                                           
                  container lan-adj-sid-sub-tlvs {        
                     description 
                        "LAN Adjacency SID optional sub-TLVs.";        
                     list lan-adj-sid-sub-tlv {
                        description 
                           "List of LAN adjacency SID sub-TLVs.";  
                        key "sid";  
                        leaf sid {            
                           type uint32;            
                           description 
                              "Segment Identifier (SID) index/label.";       
                        }       

                        leaf flags {            
                           type string;                
                           description 
                              "LAN adj-sid sub-tlv flags.         
 
                               B-Flag:  Backup Flag.  If set, the Lan-Adj-SID refers to an
                                        adjacency that is eligible for protection (e.g., using IP
                                        Fast Reroute or MPLS-FRR (MPLS-Fast Reroute) as described
                                        in Section 2.1 of [RFC8402].
  
                               V-Flag:  Value/Index Flag.  If set, then the Lan-Adj-SID carries
                                        an absolute value.  If not set, then the Lan-Adj-SID carries
                                        an index.

                               L-Flag:  Local/Global Flag.  If set, then the value/index
                                        carried by the Lan-Adj-SID has local significance.  If not
                                        set, then the value/index carried by this sub-TLV has
                                        global significance.
                     
                               S-Flag.  Set Flag. When set, the S-Flag indicates that the Lan-Adj-SID 
                                        refers to a set of adjacencies (and therefore MAY be assigned
                                        to other adjacencies as well).";
                        }
          
                        leaf mt-id {            
                           type uint8;            
                           description 
                              "Multi-topology ID.";          
                        } 
        
                        leaf weight {           
                           type uint8;           
                           description 
                              "Weight used for load-balancing.";         
                        }
          
                        leaf neighbor-router-id {            
                           type yang:dotted-quad;            
                           description 
                              "Neighbor router ID.";          
                        }              
                     }      
                   }
                }
             }

             container ri-opaque {
                description 
                  "OSPF Router Information (RI) opaque LSA.";
                   reference "RFC 7770: OSPF Router Capabilities";
 
                uses sr-algorithm-tlv;
                uses sid-range-tlvs;

            }
         }
 
         container router-lsa {
            description 
               "Router-LSAs are the Type 1 LSAs.
                The LSA describes the state and cost of the router's
                links (i.e., interfaces) to the area";
                    
            leaf flags{           
              type string;     
              description 
                 "Router LSA bits list.
                  bit V : If set, the router is an endpoint of one or 
                          more virtual link.

                  bit E : If set, the router is an AS Boundary Router (ASBR).
             
                  bit B : If set, the router is an Area Border Router (ABR).";
                  
            }  

            leaf link-count {
               type uint16;
               description 
                  "The number of links in the router LSA";
            }
    
            list link {
               key "link-id";
               description "Router LSA link.";
               uses ospfv2-router-link;
              
               leaf num-tos-metric {
                  type uint8;
                  description
                    "The number of different TOS metrics given for this link";
               }
               leaf tos-0-metric {
                  type uint16;
                  description
                    "The cost of using this router link.";
               }                            
            }
         }

         container network-lsa {
           description 
             "Network-LSAs are the Type 2 LSAs.
              The LSA describes all routers attached to the
              network, including the Designated Router itself.";

           leaf network-mask {
             type inet:ipv4-address;
             description
               "The IP address mask for the network.";
           }

           leaf-list attached-router {
              type inet:ipv4-address;
              description
                "List of the routers attached to the network.";
           }
         }

         container summary-lsa {
           description
             "Summary-LSAs are the Type 3 LSAs.
              Type3 LSAs are used when the destination is an IP network.";
           uses summary-lsa; 

         }

         container asbr-summary-lsa {
           description 
             "Asbr-summary LSAa are the Type 4 LSAs.
              Type 4 LSAs are used when the destination is an AS boundary router.";
           uses summary-lsa;
         }

         container nssa-external-lsa {
           description
             "NSSA LSA are the type 7 LSAs.
              This type 7 LSA gets translated back into a type 5 by the NSSA ABR.";

           leaf network-mask {
             type inet:ipv4-address;
             description
               "The IP address mask for the network.";
           }

           leaf metric-type {
             type cn-l3-types:ospf-metric-type;
             description
               "NSSA route metric Type";
           }

           leaf metric {
              type uint32;
              description
                 "NSSA route metric";
           }

           leaf nssa-forward-address {
             type inet:ipv4-address;
             description
               "The IP address for the neighbor.";
           }

           leaf ext-route-tag {
             type uint32;
             description
               "external route tag.";
           }
         }
      }
   }

   
   grouping prefix-sid-sub-tlvs {      
      description 
         "Prefix Segment ID (SID) sub-TLVs.";      

      container prefix-sid-sub-tlvs {        
         description 
            "Prefix SID sub-TLV.";       
 
         list prefix-sid-sub-tlv {          
            description
               "Prefix SID sub-TLV."; 
            key "sid";      

            leaf sid {           
               type uint32;           
               description 
                  "An index or label.";         
            }    

            leaf flags {            
               type string;
               description 
                  "Prefix SID Segment Identifier (SID) Flags.

                   NP-Flag:  No-PHP (Penultimate Hop Popping) Flag.  If set,
                             then the penultimate hop MUST NOT pop the Prefix-SID
                             before delivering packets to the node that advertised the
                             Prefix-SID.

                   M-Flag:  Mapping Server Flag.  If set, the SID was
                            advertised by an SR Mapping Server as described in
                            [RFC8661].

                   E-Flag:  Explicit Null Flag.  If set, any upstream neighbor
                            of the Prefix-SID originator MUST replace the Prefix-SID
                            with the Explicit NULL label (0 for IPv4) before
                            forwarding the packet.

                   V-Flag:  Value/Index Flag.  If set, then the Prefix-SID
                            carries an absolute value.  If not set, then the Prefix-
                            SID carries an index.

                   L-Flag:  Local/Global Flag.  If set, then the value/index
                            carried by the Prefix-SID has local significance.  If not
                            set, then the value/index carried by this sub-TLV has
                            global significance.";
            }     
     
            leaf mt-id {            
              type uint8;            
              description 
                 "Multi-topology ID.";          
            } 
         
            leaf algorithm {            
              type uint8;            
              description             
                "The algorithm associated with the prefix-SID.";          
            }          
         }     
      }  
   }

   grouping sr-algorithm-tlv {
      description
         "SR algorithm TLV grouping.";
      
      container sr-algorithm-tlv {
         description 
            "All SR algorithm TLVs.";
     
         leaf-list sr-algorithm {
            type uint8;
            description
               "The Segment Routing (SR) algorithms that the router is
                currently using.";
         }
      }
   }

   grouping sid-range-tlvs {
      description 
         "SID Range TLV grouping.";
    
      container sid-range-tlvs {
          description
             "List of SID range TLVs.";
  
          list sid-range-tlv {
             description
                "SID range TLV.";
             key "index"; 
 
             leaf index {
               type uint32;
               description
                  "The SID Range Index";
             }

             leaf range-size {
                type uint32; 
                description 
                   "The SID range.";
             }

             uses sid-sub-tlv; 
          }
      }
   }

   grouping ospfv2-router-link {
       description
          "OSPFv2 router link.";

       leaf link-id {
         type inet:ipv4-address;
         description
            "Router-LSA Link ID";
       }

       leaf link-data {
         type inet:ipv4-address;
         description 
            "Router-LSA Link data.";
       }

       leaf type {
         type cn-l3-types:ospf-router-link-type;
         description 
            "Router-LSA Link type.";
       }
   }

    grouping summary-lsa {
       description
          "Summary LSA";

       leaf network-mask {
           type inet:ipv4-address;
           description
             "The IP address mask for the network";
       }
       leaf metric {
         type uint32;
         description
            "Metric";
       }

    }

    grouping lsdb-instance-detail-grouping {

       list lsdb-instance-entry-detail {
         key "lsa-type lsa-id adv-router";
         config false;
         description
             "List OSPF LSAs.";
         
          uses lsa-header;
          uses lsa-header-detail;

          container as-external-lsa{
            description 
               "AS-external-LSAs are the Type 5 LSAs.";
            leaf network-mask {
               type inet:ipv4-address;
               description 
                  "IP Address mask.";
            }
            leaf metric-type {
               type cn-l3-types:ospf-metric-type;
               description 
                  "Metric Type";
            }
            leaf metric {
               type uint32;
               description 
                  "Metric";
            }
            leaf forwarding-addr {
               type inet:ipv4-address;
               description 
                  "Forwarding IP Address";
            }
            leaf route-tag {
               type uint32;
               description 
                  "A 32-bit field attached to each external route";
            }
          }
      }
   }

   grouping lsdb-interface-detail-grouping {

      list lsdb-interface-entry-detail {
         key "lsa-type lsa-id adv-router";
         config false;
         description
            "List OSPF link-scope LSAs.";

         uses lsa-header;
         uses lsa-header-detail;

         container link-local-opaque-lsa{
            description
               "Link-Local Opaque-LSA are the Type 9 LSAs.";
            leaf opaque-id  {
            type uint32;
            description
               "Opaque ID";
            }
            leaf opaque-type  {
            type uint8;
            description
               "Opaque Type";
            }
            leaf grace-period {
               type uint16;
               description
                  "Restart grace period";
            }
            leaf graceful-restart-reason {
               type cn-l3-types:ospf-gr-reason;
               description
                  "Restart reason for GR";
            }
            leaf source-address {
               type inet:ipv4-address;
               description
                  "Source Address for GR initiation";
            }
         }
      }
   }

   grouping segment-routing-state-grouping {
      description 
         "Grouping of OSPF SR state elements.";

      leaf state {
         type string; 
         config false;
         description
           "SR state enabled/disabled";
      }

      list sr-capability {
         key "router-ip";
         description
            "List of SR-Capability Info";

         leaf router-ip {
           type inet:ipv4-address;
           description
              "Router IP.";
         }
      
        leaf total-sid {
           type uint32;
           description
              "Total SIDs supported";
         }

        leaf sid-range-list-count {
           type uint32;
           description
              "SID range list count";
        }

        list sid-range {
           key "index";
           description
             "List of Ranges";
           leaf index {
           type uint32;
           description
             "SID range index for indexing";
           }

           leaf start {
             type uint32;
             description
               "SID range start";
           }

           leaf end {
             type uint32;
             description
               "SID range end";
           }

        }

        leaf algorithm {
          type uint8;
          description
            "SR algorithm";
        }

      }//SR-capability

   }//SR-state

   grouping microloop-avoidance-state-grouping {
      description
         "Grouping of OSPF microloop state elements.";

      leaf enable {
         type boolean;
         description
           "Microloop state enabled/disabled";
      }
  
      leaf rib-update-delay {
         type uint32;
         units milliseconds;
         description
           "Microloop rib-update-delay timer total configured value";
      }
     
      leaf running-state {
         type boolean;
         description
           "Microloop rib-update-delay running state";
      }
     
      leaf pending-rib-update-delay {
         type uint32;
         units milliseconds;
         description
           "Microloop rib-update-delay timer remaining value";
      }

   }
   /* Groupings */    
   grouping sid-sub-tlv {      
      description 
         "SID/Label sub-TLV grouping.";      

      container sid-sub-tlv {        
         description 
            "Used to advertise the SID/Label associated with a prefix or adjacency.";        
         leaf sid {          
            type uint32;          
            description 
               "Segment Identifier (SID) - A 20 bit label or 32 bit SID.";        
         }      
      }   
   }

   grouping ospf-instance-state-grouping {

      leaf up-time {
         type  string {
            length "0..255";
         }
         description
            "The length of time in seconds the protocol instance has been
            in the up state";
      }

      leaf lsa-count {
         type  yang:counter32;
         description
            "External Link State Advertisement count";
      }

      leaf lsa-cksum-sum {
         type  string {
            length "0..255";
         }
         description
            "External LSA checksum";
      }

      leaf originate-new-lsa-count {
         type  yang:counter32;
         description
            "Number of self-originating LSAs";
      }

      leaf rx-new-lsas-count {
         type  yang:counter32;
         description
            "Number of new LSAs received";
      }

      leaf area-count {
         type  yang:counter32;
         description
            "Number of areas in the OSPF instance";
      }

      leaf instance-creation-time {
         type  string {
            length "0..255";
         }
         description
            "OSPF Statistics Up Time";
      }

      leaf router-id-change-count {
         type  yang:counter32;
         description
            "The number of times the router ID was modified";
      }

      leaf dr-election-counter {
         type  yang:counter32;
         description
            "Number of DR elections";
      }

      leaf neighbor-expiration-count {
         type  yang:counter32;
         description
            "Number of expired neighbors";
      }

      leaf neighbor-bad-ls-reqs-count {
         type  yang:counter32;
         description
            "Number of bad LS Requests received";
      }

      leaf neighbor-seq-num-mismatch-count {
         type  yang:counter32;
         description
            "Number of packets received from neighbors with mismatched
            sequence number";
      }

      leaf router-id {
         type rt-types:router-id;
         description
            "The router identifier";
      }

      uses pdu-statistics-grouping;

      leaf router-abr-mode  {
         type  string {
            length "0..255";
          }
          description
             "OSPF router ABR mode";
      }

      leaf router-asbr  {
         type boolean;
         default "false";
         description
            "OSPF router ASBR Information";
      }

      leaf gr-helpermode-enabled {
         type boolean;
         description
            "OSPF graceful restart helper mode enabled: true/false.";
      }
      leaf helper-grace-period {
         type uint16;
         description
            "This is to get the configured OSPF GR Helper Grace Period (in seconds)";
       }
       leaf gr-restartmode-enabled {
         type boolean;
         description
            "OSPF graceful restart restarting mode enabled: true/false.";
      }
      leaf restart-grace-period {
         type uint16;
         description
            "This is to get the configured OSPF GR Restart Grace Period (in seconds)";
       }
   }

   grouping virtual-link-state-grouping {
     list virtual-link-state {
       key "name";
       description
         "Grouping of virtual link parameters";
       leaf name  {
         type  string {
           length "0..255";
         }
         description
           "Virtual link identifier, unique name assigned for the virtual link";
       }
       leaf vlink-state {
         type  cn-l3-types:ospf-vlink-state-type;
         description
           "Virtual link state";
       }
       leaf vlink-router-id {
         type rt-types:router-id;
         description
           "Router ID of remote device.";
       }
       leaf vlink-transit-area {
         type inet:ip-address;
         description
           "The transit area address of virtual link.";
       }
       leaf vlink-interface-name  {
         type  string {
         length "0..255";
         }
         description
           "Interface name from where Virtual link is connected";
       }
       leaf vlink-local-addr {
         type inet:ip-address;
         description
           "The address of local node.";
       }
       leaf vlink-remote-addr {
         type inet:ip-address;
         description
           "The address of remote node.";
       }
       leaf vlink-hello-due  {
          type  string {
            length "0..255";
          }
          description
            "This is to get the timer that tracks the remaining time before
            the neighbor is declared dead (in seconds).";
       }
       leaf vlink-hello-timer {
         type uint32;
         description
           "This is to get the configured vlink hello timer (in seconds)";
       }
       leaf vlink-dead-timer {
         type uint32;
         units seconds;
         description
           "This is to get the vlink dead timer (in seconds)";
       }
       leaf vlink-transmit-timer {
         type uint32;
         units seconds;
         description
           "This is to get the vlink transmit timer (in seconds)";
       }
       leaf vlink-retransmit-timer {
         type uint32;
         units seconds;
         description
           "This is to get the vlink retransmit timer (in seconds)";
       }
     }
   }
   grouping ospf-gr-restart-state-grouping {
      description
         "Graceful restart node state attributes.";

      leaf gr-restart-mode {
         type boolean;
         description
            "GR Restart mode of operation.";
      }
      leaf restart-grace-period {
         type uint16;
         units seconds;
         description
            "Configured OSPF GR Restart Grace Period (in seconds).";
      }
      leaf gr-restart-status{
         type  cn-l3-types:ospf-gr-status;
         description
            "Status of graceful-restart Restarting node, in progress or complete.";
      }
      leaf gr-start-timestamp {
         type string;
         description
            "Timestamp of graceful-restart start time.";
      }
      leaf gr-end-timestamp {
          type string;
          description
             "Timestamp of graceful-restart end time.";
      }
      leaf gr-remaining-time {
         type uint16;
         units seconds;
         description
            "Time(seconds) remaining for Restarting node to come out of GR as per restart-grace-period configured";
      }
      leaf gr-end-send {
         type boolean;
         description
            "GR end send to other protocols.";
      }
   }
   grouping ospf-gr-helper-state-grouping {
      description
         "Graceful helper node state attributes.";

      leaf gr-helper-mode {
         type boolean;
         description
            "GR Helper mode of operation.";
      }
      leaf gr-helper-status{
         type  cn-l3-types:ospf-gr-status;
         description
            "Status of graceful-restart Helper node, in progress or complete.";
      }
      leaf helper-start-timestamp {
         type string;
         description
            "Timestamp of GR Helper node start time.";
      }
      leaf helper-end-timestamp {
          type string;
          description
             "Timestamp of GR Helper node end time.";
      }
      leaf helper-remaining-time {
         type uint16;
         units seconds;
         description
            "Time(seconds) remaining for Helper node to come out of GR as per grace-period receivied from peer";
      }
   }
   container ospf-state
   {
      config false;
      list instance {
         key "tag";
         description
            "OSPF attributes for each ospf process id";
         leaf tag  {
            type uint32;
            description
               "OSPF process ID";
         }
         uses ospf-instance-state-grouping;

         list area-state {
            key "id";
            description
               "List of ospf areas";
            leaf id  {
               type yang:dotted-quad;
               description
                  "area to which the network belongs";
            }

            leaf interface-count  {
               type  yang:counter32;
               description
                  "Number of interface in the area";
            }

            leaf neighbor-count  {
               type  yang:counter32;
               description
                  "Number of neighbors in the area";
            }

            leaf spf-last-exec-time  {
               type  string {
                  length "0..255";
               }
               description
                  "SPF last executed time";
            }

            leaf spf-runs-count  {
               type  yang:counter32;
               description
                  "The number of times the intra-area SPF has run.
                  Discontinuities in the value of this counter can occur
                  when the OSPF area is re-initialized.";
            }

            leaf lsa-count  {
               type  yang:counter32;
               description
                  "The number of LSAs of the LSA type.";
            }

            leaf lsa-checksum  {
               type  string {
                  length "0..255";
               }
               description
                  "The modulo 2**32 sum of the LSA checksums
                  for the LSAs of this type. The value should be
                  treated as unsigned when comparing two sums of
                  checksums. While differing checksums indicate a
                  different combination of LSAs, equivalent checksums
                  don't guarantee that the LSAs are the same given that
                  multiple combinations of LSAs can result in the same
                  checksum.";
            }

            leaf area-type {
               type string {
                  length "0..12";
               }
               description
                  "type of area is Stub or NSSA";
            }

            leaf ospf-nssa-translator-role {
               description
                  "NSSA ABR's translator-role, default role is candidate";
               type enumeration {
                  enum "never" {
                     description
                        "Do not translate LSAs";
                  }

                  enum "always" {
                     description
                        "Always translate LSAs";
                  }

                  enum "candidate" {
                     description
                        "Candidate for translate LSAs";
                  }
               }
            }

            leaf ospf-nssa-translator-state {
               description
                  "State of the NSSA ABR's translator role";
               type enumeration {
                  enum "disabled" {
                     description
                        "NSSA router can not be a type-7 to type-5 LSA translator";
                  }

                  enum "enabled" {
                     description
                        "NSSA ABR can be elected as type-7 to type-5 LSA translator";
                  }

                  enum "elected" {
                     description
                        "NSSA ABR is elected for type-7 to type-5 LSA translator";
                  }
               }
            }

            container lsdb-summary-state
            {
               uses lsdb-area-summary-grouping;
            }
 
            container lsdb-detail-state
            {
               uses lsdb-area-detail-grouping;
            }
    
            container microloop-avoidance-state
            {
               uses microloop-avoidance-state-grouping;
            }

         }

         container interfaces-state
         {
            uses interface-state-grouping;
         }

         container routes-state
         {
            uses ospf-route-grouping;
         }

         list lfa-route {
            key "dest-prefix";
            description
               "List of ip LFA routes";

            leaf dest-prefix  {
               type inet:ip-prefix;
               description
                  "Destination prefix of the LFA route";
            }

            leaf dest-path-type {
               type string;
               description
                  "Destination path type attribute";
            }

            list next-hop {
               key "primary-address";
               description
                  "IPv4 next hops of the primary and alternate routes";
               leaf primary-address {
                  type inet:ip-address;
                  description
                     "Next hop ip address of the primary route";
               }

               leaf primary-interface-name  {
                  type string;
                  description
                     "Name of the outgoing interface for the primary route";
               }

               leaf alternate-address  {
                  type inet:ip-address;
                  description
                     "Next hop ip address of the alternate route";
               }

               leaf alternate-interface-name  {
                  type string;
                  description
                     "Name of the outgoing interface for the alternate route";
               }

               leaf area-id {
                  type yang:dotted-quad;
                  description
                     "OSPF Area ID";
               }

               leaf path-metric {
                  type uint32;
                  description
                     "Link cost of the alternate route";
               }

               leaf protection-provided  {
                  type string;
                  description
                     "The possible protection types provided by the alternate route";
               }
            }
         }

         list remote-lfa-route {
            key "dest-prefix";
            description
               "List of remote LFA routes";

            leaf dest-prefix  {
               type inet:ip-prefix;
               description
                  "Destination prefix of the remote LFA route";
            }

            leaf dest-path-type {
               type string;
               description
                  "Destination path type attribute";
            }

            list repair-path {
               key "primary-gateway-address";
               description
                  "IPv4 next hops of the primary and repair paths";
               leaf primary-gateway-address {
                  type inet:ip-address;
                  description
                     "Next hop ip address of the primary route";
               }

               leaf primary-interface-name  {
                  type string;
                  description
                     "Name of the outgoing interface for the primary route";
               }

               leaf tunnel-router-id  {
                  type string;
                  description
                     "Router id of the repair tunnel";
               }

               leaf tunnel-peer-address  {
                  type inet:ip-address;
                  description
                     "Peer ip address of the repair tunnel";
               }

               leaf tunnel-gateway  {
                  type inet:ip-address;
                  description
                     "Gateway ip address of the repair tunnel";
               }

               leaf tunnel-gateway-interface-name  {
                  type string;
                  description
                     "Outgoing interface name of the repair tunnel";
               }

               leaf area-id {
                  type yang:dotted-quad;
                  description
                     "OSPF Area ID";
               }

               leaf tunnel-metric {
                  type uint32;
                  description
                     "Metric of the repair tunnel";
               }

               leaf protection-provided {
                  type string;
                  description
                     "The protection scheme provided in selecting the repair tunnel";
               }
            }
         }
         list ti-lfa-route {
            key "dest-prefix";
            description
               "List of TI LFA routes";

            leaf dest-prefix  {
               type inet:ip-prefix;
               description
                  "Destination prefix of the TI LFA route";
            }

            leaf dest-path-type {
               type string;
               description
                  "Destination path type attribute";
            }

            list next-hop {
               key "primary-address";
               description
                  "IPv4 next hops of the primary and alternate routes";
               leaf primary-address {
                  type inet:ip-address;
                  description
                     "Next hop ip address of the primary route";
               }
               leaf primary-interface-name  {
                  type string;
                  description
                     "Name of the outgoing interface for the primary route";
               }

               leaf primary-router-id  {
                  type string;
                  description
                     "The primary route router id";
               }

               leaf alternate-address  {
                  type inet:ip-address;
                  description
                     "Next hop ip address of the alternate route";
               }

               leaf alternate-interface-name  {
                  type string;
                  description
                     "Name of the outgoing interface for the alternate route";
               }

               leaf alternate-router-id  {
                  type string;
                  description
                     "The alternate route router id";
               }

               leaf area-id {
                  type yang:dotted-quad;
                  description
                     "OSPF Area ID";
               }

               leaf alternate-path-metric {
                  type uint32;
                  description
                     "Link cost of the alternate route";
               }

               leaf protection-provided  {
                  type string;
                  description
                     "The protection scheme provided by the alternate route";
               }
            }
         } 

         container lsdb-summary-state
         {
            uses lsdb-instance-summary-grouping;
         }

         container lsdb-detail-state
         {
            uses lsdb-instance-detail-grouping;
         }

         container segment-routing-state
         {
            uses segment-routing-state-grouping;
         }
         container vlink-state
         {
            uses virtual-link-state-grouping; 
         } 
         container ospf-gr-restart-state
         {
            uses ospf-gr-restart-state-grouping;
         }
         container ospf-gr-helper-state
         {
            uses ospf-gr-helper-state-grouping;
         }
      }
   }

   rpc ospf-clear-instance {
      input {
         leaf instance-tag {
            type uint32 {
               range "0..65535";
            }

            description
               "OSPF instance ID";
         }

         leaf neighbor-router-id {
            type yang:dotted-quad;
            description
               "Neighbor router ID";
         }
      }

      output {
         leaf response {
            type string;
            description
               "The response could be 'success', or the reason for ospf-proc-clear failure";
         }
      }
   }

   grouping notification-instance-hdr {
      description
         "This grouping describes common instance specific,
         data for OSPF notifications.";

      leaf instance-tag {
         type uint32 {
            range "0..65535";
         }
         description
            "OSPF instance ID";
      }
   }

   grouping notification-interface {
      description
         "This grouping provides interface information,
         for the OSPF interface specific notification.";

      leaf interface {
         type string{
            length "0..255";
         }
         description
            "OSPF interface name.";
      }

      leaf if-link-type {
         type cn-l3-types:ospf-network-type;
         description
            "Link type of OSPF interface.";
      }
   }

   grouping notification-neighbor {
      description
         "This grouping provides the neighbor information,
         for neighbor specific notifications.";

      leaf neighbor-router-id {
         if-feature router-id;
         type rt-types:router-id;
         description
            "Neighbor router ID.";
      }

      leaf neighbor-ip-addr {
         type inet:ip-address;
         description
            "Neighbor address.";
      }
   }

   notification ospf-neighbor-events {
      list neighbor {
         description
            "Defines OSPF neighbor state change events and associated data used to publish change in the state";
         uses notification-interface;
         uses notification-instance-hdr;
         uses notification-neighbor;

         leaf old-state {
            type cn-l3-types:ospf-nbr-state-type;
            description
               "Old OSPF neighbor state.";
         }

         leaf new-state {
            type cn-l3-types:ospf-nbr-state-type;
            description
               "New OSPF neighbor state.";
         }
      }
   }

   notification ospf-instance-events {
      list instance {
         description
            "Defines OSPF instance state change events and associated data used to publish change in the state";
         leaf tag {
            type uint32 {
               range "0..65535";
            }
            description
               "OSPF instance ID";
         }
         leaf router-id {
            if-feature router-id;
            type rt-types:router-id;
            description
               "Defined in RFC 2328. A 32-bit number
                that uniquely identifies the router.";
         }
         leaf state {
            type cn-l3-types:ospf-inst-state-type;
            description
               "OSPF instance state.";
         }
         leaf duplicate-router-id-intra-area {
            type boolean;
            description
               "OSPF duplicate router-id detected in same area.";
         }
         leaf duplicate-router-id-asbr {
            type boolean;
            description
               "OSPF duplicate router-id detected with ASBR.";
         }
      }
   }

   notification ospf-gr-status-event {
      description
         "Defines status of OSPF graceful restart/helper mode";

      leaf gr-mode {
         type enumeration {
            enum restart {
               description
                  "Indicates OSPF GR restarting mode";
            }
            enum helper {
               description
                  "Indicates OSPF GR helper mode";
            }
         }
         description
            "OSPF GR mode of operation.";
      }
      leaf gr-status {
         type enumeration {
            enum enter {
               description
                  "Entering into OSPF GR restart/helper mode";
            }
            enum exit {
               description
                  "Exiting from OSPF GR restart/helper mode";
            }
         }
         description
            "Describe OSPF GR enter/exit status.";
      }
   }

   notification ospf-sec-network-event {
      description
         "Defines events in case of area mismatch between primary and secondary networks in OSPF";

      leaf interface {
         type string {
            length "0..255";
         }
         description
            "OSPF interface name";
      }

      leaf secondary-network-addr {
         type inet:ipv4-prefix;
         description
            "The secondary network address configured in OSPF";
      }

      leaf primary-network-addr {
         type inet:ipv4-prefix;
         description
            "The primary network address configured in OSPF";
      }

      leaf area-id  {
         type yang:dotted-quad;
         description
            "Area Id in quad-dotted notation";
      }
   }
}
