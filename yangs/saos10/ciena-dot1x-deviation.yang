module ciena-dot1x-deviation {
    yang-version 1.1;
    namespace "http://www.ciena.com/ns/yang/ciena-dot1x-deviation";
    prefix "cn-dot1x-dev";

    import ciena-dot1x {
       prefix "cn-dot1x";
    }

    import openconfig-system {
       prefix "oc-sys";
    }

  organization
    "Ciena Corporation";

  contact
    "Web URL: http://www.ciena.com/
     E-mail:  yang@ciena.com
     Postal:  7035 Ridge Road
              Hanover, Maryland 21076
              U.S.A.
     Phone:   +1 800-921-1144
     Fax:     +1 410-694-5750";

  description
    "This YANG module defines Ciena's deviations from the ciena-dot1x
     model.

     Copyright (c) 2019 Ciena Corporation.  All rights reserved.

     All information contained herein is, and remains the property of
     Ciena Corporation. Dissemination of this information or
     reproduction of this material is strictly forbidden unless prior
     written permission is obtained from Ciena Corporation.";

   revision "2019-04-25" {
     description
        "Added deviations to ciena-dot1x.yang model.";
     reference
        "";
   }

   deviation "/oc-sys:system/cn-dot1x:dot1x/cn-dot1x:config/cn-dot1x:authentication-method" {
     deviate add {
      max-elements 1;
     }
   }

   deviation "/oc-sys:system/cn-dot1x:dot1x/cn-dot1x:config/cn-dot1x:accounting-method" {
     deviate add {
      max-elements 1;
     }
  }
}
