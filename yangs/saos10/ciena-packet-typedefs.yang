module ciena-packet-typedefs {
  namespace "http://www.ciena.com/ns/yang/ciena-packet-typedefs";
  prefix cntypes;

  organization
    "Ciena Corporation";
  contact
    "Web URL: http://www.ciena.com/
     Postal:  7035 Ridge Road
             Hanover, Maryland 21076
             U.S.A.
     Phone:   +1 800-921-1144
     Fax:     +1 410-694-5750";
  description
    "This YANG module defines Ciena's commonly used typedefs

     Copyright (c) 2022 Ciena Corporation.  All rights
     reserved.

     All information and intellectual property contained in this
     YANG module (Specification) is, and remains the property
     of Ciena Corporation. Ciena retains all title and ownership
     in the Specification, including any revisions.

     Ciena grants all interested parties that access the
     Specification with the intent to use or distribute (you) a
     non-exclusive, no-cost license to use and distribute
     unmodified copies of the Specification solely in connection
     with the management of Ciena products sold by or on
     behalf of Ciena, provided this copyright notice and license
     appear on all copies. Ciena may rescind or modify this
     license at any time.

     This Specification is supplied 'as is', and Ciena makes no
     warranty, either express or implied, as to the use, operation,
     condition, or performance of the Specification. You agree
     that Ciena has no liability for your use of the Specification.";

  revision "2023-12-07" {
    description
      "Added new xcvr-modes 70-400-E, 65-400-E,
       60-400-E-ZR and 60-400-E-ZR+.";
  }

  revision "2023-11-01" {
    description
      "Added new types for pon-olt-state";
  }

  revision 2023-09-11 {
    description
      "Added new pkt-max XCVR mode 70400E";
  }

  revision 2023-03-22 {
    description
      "Added new XCVR types SFP56 and mode 50GE.";
  }

  revision 2023-02-13 {
    description
      "Added new XCVR mode 58-200.";
  }

  revision 2022-10-02 {
    description
      "Added new XCVR types SFPDD.";
  }

  revision 2022-08-05 {
    description
      "Added new XCVR modes 400GZR, 400GZR+, PKT-MAX-200 and PKT-MAX-400.";
  }

  revision 2022-06-14 {
    description
      "Added new XCVR mode 70-400";
  }

  revision 2022-05-31 {
    description
      "Added QSFPDD WaveLogic 5n Type";
  }

  revision 2022-04-06 {
    description
      "Added Fabric Cable Types";
  }

  revision 2022-01-14 {
    description
      "Added new XCVR type for Fix Copper XCVRs.
       Modified PN bytes from 7 to 8 (added a extra F) for combo TDM XCVR and changed type";
  }

  revision 2021-11-25 {
    description
      "Added new XCVR modes 31.5-100, 31.5-200, 63-200 and 63-400.";
  }

  revision 2021-09-07 {
    description
      "Added new enum type grid-spac-enum
       Changed modem-frequency fraction digits from 1 to 3";
  }

  revision 2021-08-25 {
    description
      "Update tx-power-lvl range from -9.0..4.0 to -13.0..4.0";
  }

  revision 2020-04-02 {
    description
      "Added new XCVR modes for TDM native ports.
       Added new XCVR types QSFP56 and QSFPDD.
       Added new XCVR mode 200GE.
       Updated lanes-number range from 0..4 to 0..8
       Added new XCVR type SFP28.";
  }

  revision 2020-01-10 {
    description
      "Added fingerprint types";
  }

  revision 2019-10-10 {
    description
      "Added new values to xcvr-mode and xcvr-type enums.";
  }

  revision 2019-03-20 {
    description
      "Added Xcvr types and mode";
  }

  revision 2018-05-17 {
    description
      "Based off of ciena-waveserver-typedefs.yang";
  }

  typedef fingerprint {
    type string {
      pattern '(sha-256:([A-F0-9]{2}:){31}[A-F0-9]{2})|(sha-1:([A-F0-9]{2}:){19}[A-F0-9]{2})';
    }
    description
      "SHA-1 or SHA-256 fingerprint";
  }

  typedef mac-string {
    type string {
      length "1..20";
    }
    description
      "MAC address string.";
  }

  typedef name-string {
    type string {
      length "1..32";
    }
    description
      "String type for object names used in Ciena defined modules. It must be a
       non empty string that is at most 32 characters long.";
  }

  typedef description-string {
    type string {
      length "0..128";
    }
    description
      "String type for description used in Ciena defined modules. Max length of
       128 characters, plus null.";
  }

  typedef on-off-enum {
    type enumeration {
      enum "off" {
        description
          "Off";
      }
      enum "on" {
        description
          "On";
      }
    }
    description
      "Off and On enum toggle used in Ciena defined modules.";
  }

  typedef power-state {
    type enumeration {
      enum "automatic" {
        description
          "Power state is automatic (on/normal).";
      }
      enum "shutdown" {
        description
          "Power state is shutdown (off/low-power-mode).";
      }
    }
    description
      "Power state automatic (on/normal) or shutdown (off/low-power-mode).";
  }

  typedef yes-no-enum {
    type enumeration {
      enum "no" {
        description
          "No";
      }
      enum "yes" {
        description
          "Yes";
      }
    }
    description
      "No and Yes enum toggle used in Ciena defined modules.";
  }

  typedef up-down-enum {
    type enumeration {
      enum "down" {
        description
          "Object is down/disabled/failed.";
      }
      enum "up" {
        description
          "Object is up/operational.";
      }
    }
    description
      "Down and Up enum toggle used in Ciena defined modules.";
  }

  typedef enabled-disabled-enum {
    type enumeration {
      enum "disabled" {
        description
          "Object or attribute is disabled.";
      }
      enum "enabled" {
        description
          "Object or attribute is enabled.";
      }
    }
    description
      "Enabled and Disabled enum toggle used in Ciena defined modules.";
  }

  typedef ettp-fec-enum {
     type enumeration {
        enum "auto" {
           description
              "Object or attribute value is automatic";
        }    
        enum "disabled" {
           description
              "Object or attribute is disabled.";
        }
        enum "enabled" {
           description
              "Object or attribute is enabled.";
        }
     }
     description
        "Different state for Ettp forward-error-correction";
  }

  typedef yes-no-na-enum {
    type enumeration {
      enum "no" {
        description
          "No";
      }
      enum "yes" {
        description
          "Yes";
      }
      enum "not-applicable" {
        description
          "Not applicable";
      }
    }
    description
      "No and Yes enum toggle used in Ciena defined modules.";
  }

  typedef enabled-disabled-na-enum {
    type enumeration {
      enum "disabled" {
        description
          "Disabled";
      }
      enum "enabled" {
        description
          "Enabled";
      }
      enum "not-applicable" {
        description
          "Not applicable";
      }
    }
    description
      "Enabled, Disabled, and not-applicable enum used in Ciena defined modules.";
  }

  typedef wl-spacing {
    type enumeration {
      enum "50GHz" {
        description
          "50GHz wavelength spacing.";
      }
      enum "100GHz" {
        description
          "100GHz wavelength spacing.";
      }
      enum "200GHz" {
        description
          "200GHz wavelength spacing.";
      }
      enum "flex-grid" {
        description
          "Flex-grid wavelength spacing.";
      }
    }
    description
      "Wavelength spacing, 50GHz, 100GHz, 200GHz, or flex-grid. Only 'flex-grid'
       supported in Waveserver Ai R1.0.";
  }

  typedef pon-olt-state {
    type enumeration {
      enum "active" {
        description
          "PON OLT is in Active State.";
      }
      enum "standby" {
        description
          "PON OLT is in Standby State.";
      }
      enum "not-redundant" {
        description
          "PON OLT is in Not Participating in a Redundancy setup.";
      }
    }
    description
      "PON OLT active/standby state.";
  }

  typedef decimal-3-dig {
    type decimal64 {
      fraction-digits 3;
      range "-2147483.0 .. 2147483.0";
    }
    description
      "Decimal value up to 3 digits.";
  }

  typedef decimal-2-dig-small {
    type decimal64 {
      fraction-digits 2;
      range "-30000.0 .. 30000.0";
    }
    description
      "Decimal value up to 2 digits.";
  }

  typedef decimal-2-dig {
    type decimal64 {
      fraction-digits 2;
      range "-21474836.0 .. 21474836.0";
    }
    description
      "Decimal value up to 2 digits.";
  }

  typedef decimal-1-dig {
    type decimal64 {
      fraction-digits 1;
      range "-214748364.0 .. 214748364.0";
    }
    description
      "Decimal value up to 1 digits.";
  }

  typedef string-sci {
    type string {
      length "0..32";
      pattern '[-+]?[0-9](\.[0-9]+)?([eE][-+]?[0-9]+)?';
    }
    description
      "String in Scientific Notation format with a max length of 32 characters.";
  }

  typedef string-maxl-15 {
    type string {
      length "0..15";
    }
    description
      "Standard string that has a max length of 15 characters. Can be used for
       various nodes that may require string of this length.";
  }

  typedef string-maxl-16 {
    type string {
      length "0..16";
    }
    description
      "Standard string that has a max length of 16 characters. Can be used for
       various nodes that may require string of this length.";
  }

  typedef string-maxl-32 {
    type string {
      length "0..32";
    }
    description
      "Standard string that has a max length of 32 characters. Can be used for
       various nodes that may require string of this length.";
  }

  typedef string-maxl-44 {
    type string {
      length "0..44";
    }
    description
      "Standard string that has a max length of 44 characters. Can be used for
       various nodes that may require string of this length.";
  }

  typedef string-maxl-50 {
    type string {
      length "0..50";
    }
    description
      "Standard string that has a max length of 50 characters. Can be used for
       various nodes that may require string of this length.";
  }

  typedef string-maxl-64 {
    type string {
      length "0..64";
    }
    description
      "Standard string that has a max length of 64 characters. Can be used for
       various nodes that may require string of this length.";
  }

  typedef string-maxl-128 {
    type string {
      length "0..128";
    }
    description
      "Standard string that has a max length of 128 characters. Can be used for
       various nodes that may require string of this length.";
  }

  typedef string-maxl-254 {
    type string {
      length "0..254";
    }
    description
      "Standard string that has a max length of 254 characters. Can be used for
       various nodes that may require string of this length.";
  }

  typedef string-maxl-256 {
    type string {
      length "0..256";
    }
    description
      "Standard string that has a max length of 256 characters. Can be used for
       various nodes that may require string of this length.";
  }

  typedef ipaddr-or-hostname {
    type string {
      length "1..63";
    }
    description
      "IP address or hostname string.";
  }

  typedef ipv4-address {
    type string {
      length "0..16";
      pattern
         '(([0-9]|[1-9][0-9]|1[0-9][0-9]|2[0-4][0-9]|25[0-5])\.){3}'
       +  '([0-9]|[1-9][0-9]|1[0-9][0-9]|2[0-4][0-9]|25[0-5])';
    }
    description
      "An IPv4 address represented in dotted decimal notation.";
  }

  typedef ipv4-prefix {
    type string {
      length "0..20";
      pattern
         '(([0-9]|[1-9][0-9]|1[0-9][0-9]|2[0-4][0-9]|25[0-5])\.){3}'
       +  '([0-9]|[1-9][0-9]|1[0-9][0-9]|2[0-4][0-9]|25[0-5])'
       + '/(([0-9])|([1-2][0-9])|(3[0-2]))';
    }
    description
      "An IPv4 address and prefix represented in dotted decimal notation
       followed by a slash and a prefix length, e.g. '192.168.1.2/24'.";
  }

  typedef ipv4-opt-prefix {
    type string {
      length "0..20";
      pattern
         '(([0-9]|[1-9][0-9]|1[0-9][0-9]|2[0-4][0-9]|25[0-5])\.){3}'
       +  '([0-9]|[1-9][0-9]|1[0-9][0-9]|2[0-4][0-9]|25[0-5])'
       + '(/(([0-9])|([1-2][0-9])|(3[0-2])))?';
    }
    description
      "A string type matching either the ipv4-address format or the
       ipv4-prefix format. That is, an IPv4 address in dotted decimal
       notation with an optional slash and prefix length.";
  }

  typedef port-name {
    type string {
      length "1..32";
    }
    description
      "A string representing a port interface name. Format is: '<slot>-<port>'
       or '<slot>-<majorport>.<minorport>'.";
  }

  typedef service-idx {
    type uint32 {
      range "0 .. 1000";
    }
    description
      "Service Index";
  }

  typedef service-domain-idx {
    type uint32 {
      range "0 .. 20";
    }
    description
      "Service Domain Index";
  }

  typedef xcvr-type {
    type enumeration {
      enum "not-available" {
        value 0;
        description
          "XCVR type not available.";
      }
      enum "unsupported" {
        value 1;
        description
          "XCVR type unsupported.";
      }
      enum "QSFPplus" {
        value 2;
        description
          "XCVR type QSFP+.";
      }
      enum "QSFP28" {
        value 3;
        description
          "XCVR type QSFP28.";
      }
      enum "WaveLogic 3 Extreme" {
        value 4;
        description
          "XCVR type WL3e.";
      }
      enum "WaveLogic Ai" {
        value 5;
        description
          "XCVR type WLAi.";
      }
      enum "Sgmii" {
        value 6;
        description
          "XCVR type Sgmii.";
      }
      enum "CFP" {
        value 7;
        description
          "XCVR type CFP.";
      }
      enum "SFP" {
        value 8;
        description
          "XCVR type SFP.";
      }
      enum "SFPplus"
      {
        value 9;
        description
          "XCVR type SFP Plus.";
      }
      enum "XFP"
      {
        value 10;
        description
          "XCVR type XFP.";
      }
      enum "SFPplus tdwdm"
      {
         value 11;
         description
            "XCVR type SFPplus tdwdm.";
      }
      enum "CFP2"
      {
         value 12;
         description
            "XCVR type CFP2.";
      }
      enum "CFP2-DCO"
      {
         value 13;
         description
            "XCVR type CFP2-DCO.";
      }
      enum "CFP2-ACO"
      {
         value 14;
         description
            "XCVR type CFP2-ACO.";
      }
      enum "CEP001-OC3"
      {
         value 15;
         description
            "XCVR type CEP001-OC3.";
      }
      enum "CEP002-OC3-OC12"
      {
         value 16;
         description
            "XCVR type CEP002-OC3-OC12.";
      }
      enum "CEP003-DS3-E3"
      {
         value 17;
         description
            "XCVR type CEP003-DS3-E3.";
      }
      enum "GES101-OC3-STM1"
      {
         value 18;
         description
            "XCVR type GES101-OC3-STM1.";
      }
      enum "TDM2GE-E1"
      {
         value 19;
         description
            "XCVR type TDM2GE-E1.";
      }
      enum "TDM4GE-DS1"
      {
         value 20;
         description
            "XCVR type TDM4GE-DS1.";
      }
      enum "TSOP01-OC3-STM1"
      {
         value 21;
         description
            "XCVR type TSOP01-OC3-STM1.";
      }
      enum "TSOP02-OC12-STM4"
      {
         value 22;
         description
            "XCVR type TSOP02-OC12-STM4.";
      }
      enum "TSOP03-OC48-STM16"
      {
         value 23;
         description
            "XCVR type TSOP03-OC48-STM16.";
      }
      enum "NATIVE-OC3-OC12"
      {
         value 24;
         description
            "XCVR type NATIVE-OC3-OC12.";
      }
      enum "NATIVE-OC48"
      {
         value 25;
         description
            "XCVR type NATIVE-OC48.";
      }
      enum "QSFP56"
      {
         value 26;
         description
            "XCVR type QSFP56.";
      }
      enum "QSFPDD"
      {
         value 27;
         description
            "XCVR type QSFPDD.";
      }
      enum "SFP28"
      {
         value 28;
         description
            "XCVR type SFP28.";
      }
      enum "Fixed-Copper"
      {
         value 29;
         description
            "XCVR type fixed copper.";
      }
      enum "SFPDD"
      {
         value 30;
         description
            "XCVR type SFPDD.";
      }
      enum "QSFPDD-AOC"
      {
         value 31;
         description
            "XCVR type QSFPDD-AOC.";
      }
      enum "QSFPDD-DAC"
      {
         value 32;
         description
            "XCVR type QSFPDD-DAC.";
      }
      enum "QSFPDD-WaveLogic-5n"
      {
         value 33;
         description
            "XCVR type QSFPDD-WaveLogic-5n.";
      }
      enum "SFP56"
      {
         value 34;
         description
            "XCVR type SFP56.";
      }

    }
    description
      "Transceiver type.";
  }

  typedef xcvr-mode {
    type enumeration {
      enum "blank" {
        description
          "XCVR/slot is blank.";
      }
      enum "auto" {
        description
          "Various speed XCVRs can be inserted (e.g. 40GbE versus 100GbE)  
           as long as the hardware supports them, and the system will
           automatically adjust the port speed based on the XCVRs
           capabilities. For multi rate XCVRs, the highest speed 
           supported will be selected.";
      }
      enum "100M" {
        description
          "XCVR mode FastEthernet.";
      }
      enum "1GE" {
        description
          "XCVR mode 1 Gigabit Ethernet.";
      }
      enum "10GE" {
        description
          "XCVR mode 10 Gigabit Ethernet.";
      }
      enum "25GE" {
         description
           "XCVR mode 25 Gigabit Ethernet.";
      }
      enum "40GE" {
        description
          "XCVR mode 40 Gigabit Ethernet.";
      }
      enum "100GE" {
        description
          "XCVR mode 100 Gigabit Ethernet.";
      }
      enum "400GE" {
        description
          "XCVR mode 400 Gigabit Ethernet.";
      }

      // Line XCVR Modes - Baud/Modulation Values
      enum "35-100" {
        description
          "XCVR mode 35Gbaud, 100Gbps.";
      }
      enum "35-200" {
        description
          "XCVR mode 35Gbaud, 200Gbps.";
      }
      enum "56-100" {
        description
          "XCVR mode 56Gbaud, 100Gbps.";
      }
      enum "56-200" {
        description
          "XCVR mode 56Gbaud, 200Gbps.";
      }
      enum "56-300" {
        description
          "XCVR mode 56Gbaud, 300Gbps.";
      }
      enum "56-400" {
        description
          "XCVR mode 56Gbaud, 400Gbps.";
      }
      enum "28-100" {
        description
          "XCVR mode 28Gbaud, 100Gbps.";
      }
      enum "32-100" {
        description
          "XCVR mode 32Gbaud, 100Gbps.";
      }
      enum "32-200" {
        description
          "XCVR mode 32Gbaud, 200Gbps.";
      }
      enum "DS1-E1" {
        description
          "XCVR mode DS1-E1.";
      }
      enum "DS3-E3" {
        description
          "XCVR mode DS3-E3.";
      }
      enum "OC3-STM1" {
        description
          "XCVR mode OC3-STM1.";
      }
      enum "OC12-STM4" {
        description
          "XCVR mode OC12-STM4.";
      }
      enum "OC48-STM16" {
        description
          "XCVR mode OC48-STM16.";
      }
      enum "NATIVE-OC3-STM1" {
        description
          "XCVR mode NATIVE-OC3-STM1.";
      }
      enum "NATIVE-OC12-STM4" {
        description
          "XCVR mode NATIVE-OC12-STM4.";
      }
      enum "NATIVE-OC48-STM16" {
        description
          "XCVR mode NATIVE-OC48-STM16.";
      }
      enum "200GE" {
        description
          "XCVR mode 200 Gigabit Ethernet.";
      }
      enum "31.5-100" {
        description
          "XCVR mode 31.5Gbaud, 100Gbps.";
      }
      enum "31.5-200" {
        description
          "XCVR mode 31.5Gbaud, 200Gbps.";
      }
      enum "63-200" {
        description
          "XCVR mode 63Gbaud, 200Gbps.";
      }
      enum "63-400" {
        description
          "XCVR mode 63Gbaud, 400Gbps.";
      }
      enum "70-400" {
        description
          "XCVR mode 70Gbaud, 400Gbps.";
      }
      enum "400GZR" {
        description
          "XCVR mode ZR 400Gbps.";
      }
      enum "400GZR+" {
        description
          "XCVR mode ZR+ 400Gbps.";
      }
      enum "PKT-MAX-200" {
        description
          "XCVR mode Packet max 200Gbps.";
      }
      enum "PKT-MAX-400" {
        description
          "XCVR mode Packet max 400Gbps.";
      }
      enum "58-200" {
        description
          "XCVR mode 58Gbaud, 200Gbps.";
      }
      enum "70-400-E" {
        description
          "XCVR mode 70Gbaud, 400Gbps, Ethernet transcoded.";
      }
      enum "65-400-E" {
        description
          "XCVR mode 65Gbaud, 400Gbps, Ethernet transcoded, PKT-MAX.";
      }
      enum "60-400-E-ZR" {
        description
          "XCVR mode 60Gbaud, 400Gbps, Ethernet transcoded, ZR.";
      }
      enum "60-400-E-ZR+" {
        description
          "XCVR mode 60Gbaud, 400Gbps, Ethernet transcoded, ZR+.";
      }
      enum "50GE" {
        description
          "XCVR mode 50 Gigabit Ethernet.";
      }
      enum "PKT-MAX-70400E" {
        description
          "XCVR mode 70Gbaud, 400Gbps ";
      }

    }
    description
      "Transceiver mode.";
  }

  typedef xcvr-fec-type {
    type enumeration {
      enum "GFEC" {
        description
          "XCVR GFEC type.";
      }
      enum "EFEC" {
        description
          "XCVR EFEC type.";
      }
    }
    description
      "Transceiver FEC type.";
  }

  typedef line-sys-enum {
    type enumeration {
      enum "coloured" {
        description
          "Line system coloured.";
      }
      enum "colourless" {
        description
          "Line system colourless.";
      }
      enum "contentionless" {
        description
          "Line system contentionless.";
      }
      enum "cs-coloured" {
        description
          "Line system cs-coloured.";
      }
      enum "cs-colourless" {
        description
          "Line system cs-colourless.";
      }
    }
    description
      "Line system type.";
  }

  typedef lanes-number {
    type uint16 {
      range "0 .. 8";
    }
    description
      "Lane number common type, lane range is defined from 0 to 8.";
  }

  typedef connector-type-desc-enum {
    type enumeration {
      enum "Unknown or unspecified" {
        value 0;
        description
          "Unknown or unspecified.";
      }
      enum "SC - Subscriber Connector" {
        value 1;
        description
          "SC - Subscriber Connector.";
      }
      enum "Fibre Channel Style 1 copper connector" {
        value 2;
        description
          "Fibre Channel Style 1 copper connector.";
      }
      enum "Fibre Channel Style 2 copper connector" {
        value 3;
        description
          "Fibre Channel Style 2 copper connector.";
      }
      enum "BNC/TNC - Bayonet/Threaded Neill-Concelman" {
        value 4;
        description
          "BNC/TNC - Bayonet/Threaded Neill-Concelman.";
      }
      enum "Fibre Channel coax headers" {
        value 5;
        description
          "Fibre Channel coax headers.";
      }
      enum "Fiber Jack" {
        value 6;
        description
          "Fiber Jack.";
      }
      enum "LC - Lucent Connector" {
        value 7;
        description
          "LC - Lucent Connector.";
      }
      enum "MT-RJ - Mechanical Transfer - Registered Jack" {
        value 8;
        description
          "MT-RJ - Mechanical Transfer - Registered Jack.";
      }
      enum "MU - Multiple Optical" {
        value 9;
        description
          "MU - Multiple Optical.";
      }
      enum "SG" {
        value 10;
        description
          "SG.";
      }
      enum "Optical Pigtail" {
        value 11;
        description
          "Optical Pigtail.";
      }
      enum "MPO 1x12 - Multifiber Parallel Optic" {
        value 12;
        description
          "MPO 1x12 - Multifiber Parallel Optic.";
      }
      enum "MPO 2x16" {
        value 13;
        description
          "MPO 2x16.";
      }
      enum "HSSDC II - High Speed Serial Data Connector" {
        value 32;
        description
          "HSSDC II - High Speed Serial Data Connector.";
      }
      enum "Copper pigtail" {
        value 33;
        description
          "Copper pigtail.";
      }
      enum "RJ45 - Registered Jack" {
        value 34;
        description
          "RJ45 - Registered Jack.";
      }
      enum "No separable connector" {
        value 35;
        description
          "No separable connector.";
      }
      enum "MXC 2x16" {
        value 36;
        description
          "MXC 2x16.";
      }
    }
    description
      "Human readable description of Vendor's connector type byte value.";
    reference
      "SFF-8024, table 4-3";
  }

  typedef modem-frequency {
    type decimal64 {
      fraction-digits 3;
    }
    units "GHz";
    description
      "Modem frequency, in GHz. 0.0 indicates unprovisioned (default) value. L-Band
       range is 186087.500 - 190956.200 GHz, and C-Band range is 191100.000 - 196150.000 GHz.";
  }

  typedef modem-class {
    type enumeration {
      enum "terrestrial" {
        description
          "Terrestrial modem class.";
      }
      enum "submarine" {
        description
          "Submarine modem class.";
      }
      enum "unavailable" {
        description
          "Modem class is unavailable.";
      }
    }
    description
      "The modem class type, terrestrial or submarine.";
  }

  typedef link-optimization-mode {
    type enumeration {
      enum "standard" {
        description
          "Standard Mode - Default setting which provides best SNR performance.";
      }
      enum "snr-tolerant" {
        description
          "SNR Tolerant Mode - Recommended for applications that want to
           achieve maximum SNR tolerance while still providing reasonable
           polarization tracking speed and PDL tolerance.";
      }
      enum "fast-tracking" {
        description
          "Fast Tracking Mode - Recommended for applications that want to
           maximize SOP tracking.";
      }
      enum "spectral-efficiency" {
        description
          "Spectral Efficiency Mode - Recommended for applications that want
           to maximize spectral efficiency by minimizing spectral signal width.";
      }
      enum "latency" {
        description
          "Low Latency Mode - Recommended for applications that want to
           minimize transmission latency.";
      }
      enum "foreign" {
        description
          "Foreign Line Mode - Recommended for applications that require the
           transmitted signal to be be recognized/controlled by a foreign line
           system.";
      }
      enum "narrow" {
        description
          "Narrow Channel Mode - Recommended for applications that want to
           achieve maximum SNR tolerance over heavily filtered optical link.";
      }
      enum "non-linear" {
        description
          "Non-Linear Channel Mode - Recommended for applications that want
           to achieve maximum SNR tolerance on a non-linear fiber link.";
      }
      enum "reserved-1" {
        description
          "Reserved Mode 1.";
      }
      enum "reserved-2" {
        description
          "Reserved Mode 2.";
      }
      enum "reserved-3" {
        description
          "Reserved Mode 3.";
      }
      enum "custom" {
        description
          "Custom Link Optimization Mode.";
      }
    }
    description
      "Link Optimization Modes for the WaveLogic modems.";
  }

  typedef supported-link-optimization-modes {
    type bits {
      bit standard {
        description
          "Supports standard link-optimization-mode.";
      }
      bit snr-tolerant {
        description
          "Supports snr-tolerant link-optimization-mode.";
      }
      bit fast-tracking {
        description
          "Supports fast-tracking link-optimization-mode.";
      }
      bit spectral-efficiency {
        description
          "Supports spectral-efficiency link-optimization-mode.";
      }
      bit latency {
        description
          "Supports latency link-optimization-mode.";
      }
      bit foreign {
        description
          "Supports foreign link-optimization-mode.";
      }
      bit narrow {
        description
          "Supports narrow link-optimization-mode.";
      }
      bit non-linear {
        description
          "Supports non-linear link-optimization-mode.";
      }
      bit reserved-1 {
        description
          "Supports reserved-1 link-optimization-mode.";
      }
      bit reserved-2 {
        description
          "Supports reserved-2 link-optimization-mode.";
      }
      bit reserved-3 {
        description
          "Supports reserved-3 link-optimization-mode.";
      }
      bit custom {
        description
          "Supports custom link-optimization-mode.";
      }
    }
    description
      "Type definition for supported link-optimization-mode values for PTPs
       associated with modem XCVR objects.";
  }

  typedef tx-power-lvl {
    type decimal64 {
      fraction-digits 1;
      range "-13.0 .. 4.0";
    }
    units "dBm";
    description
      "Modem Tx Power Level.";
  }

  typedef module-type-enum {
    type enumeration {
      enum "unknown" {
        description
          "Module type unknown.";
      }
      enum "integrated" {
        description
          "Module type integrated.";
      }
      enum "field-replaceable" {
        description
          "Module type field-replaceable.";
      }
    }
    description
      "Module type enum.";
  }

  typedef module-type-bits {
    type bits {
      bit integrated {
        position 0;
        description
          "Module type integrated.";
      }
      bit field-replaceable {
        position 1;
        description
          "Module type field-replaceable.";
      }
    }
    description
      "Module type bits.";
  }

  typedef restart-reason {
    type enumeration {
      enum "unknown" {
        description
          "Unknown restart reason.";
      }
      enum "user-warm" {
        description
          "User-initiated warm restart.";
      }
      enum "user-cold" {
        description
          "User-initiated cold restart.";
      }
      enum "system-warm" {
        description
          "System-initiated warm restart.";
      }
      enum "system-cold" {
        description
          "System-initiated cold restart.";
      }
      enum "power-on" {
        description
          "Device inserted or powered on.";
      }
    }
    description
      "Chassis/Module last restart reason.";
  }

  typedef conditioning-type {
    type enumeration {
      enum "none" {
        value 0;
        description
          "No consequent action.";
      }
      enum "laser-off" {
        value 1;
        description
          "Disable the transmitter consequent action.";
      }
      enum "ethernet" {
        value 2;
        description
          "Ethernet Local Fault consequent action.";
      }
      enum "otn" {
        value 3;
        description
          "OTN consequent action as defined in ITU-T G.798.";
      }
    }
    description
      "Egress UNI port consequent action for an EPL service to be applied on a
       far-end ingress UNI failure or network failure.";
  }

  typedef conditioning-holdoff {
    type int16 {
      range "0|10|20|30|40|50|60|70|80|90|100|200|300|400|500|600|700|800|900|1000";
    }
    units "ms";
    description
      "Number of milliseconds to delay Egress UNI port consequent action for an
       EPL service.";
  }

  typedef trace-mismatch-mode {
    type enumeration {
      enum "operator-only" {
        value 1;
        description
          "Trace mismatch detection criteria includes operator-specific trace
           string only. Other fields are ignored.";
      }
      enum "sapi" {
        value 2;
        description
          "Trace mismatch detection criteria includes source access point
           identifier (SAPI) trace string only. Other fields are ignored.";
      }
      enum "dapi" {
        value 3;
        description
          "Trace mismatch detection criteria includes destination access point
           identifier (DAPI) trace string only. Other fields are ignored.";
      }
      enum "sapi-and-dapi" {
        value 4;
        description
          "Trace mismatch detection criteria includes SAPI and DAPI strings. A
           mismatch of either of these fields will result in TTI mismatch. The
           operator specific field is ignored.";
      }
    }
    description
      "The trail trace identifier (TTI) mismatch mode, indicating which fields of
       the TTI overhead are used for trace mismatch detection.";
  }

  typedef trace-mismatch-fail-mode {
    type enumeration {
      enum "none" {
        description
          "TTI mismatch detection is disable or ignored. Do not raise an alarm on
           TTI mismatch condition.";
      }
      enum "alarm-only" {
        description
          "Raise an alarm when TTI mismatch occurs, but do not squelch traffic.";
      }
      enum "squelch-traffic" {
        description
          "Squelch the traffic via signal conditioning when TTI mismatch occurs.";
      }
    }
    description
      "The trail trace identifier (TTI) mismatch failure mode. When TTI mismatch
       condition occurs, this indicates the consequent action taken, e.g. whether
       or not to raise an alarm.";
  }

  typedef grid-spac-enum {
    type enumeration {
      enum "6.25GHz" {
        description
          "Grid spacing 6.25GHz.";
      }
      enum "50GHz" {
        description
          "Grid spacing 50GHz.";
      }
      enum "75GHz" {
        description
          "Grid spacing 75GHz.";
      }
      enum "100GHz" {
        description
          "Grid spacing 100GHz.";
      }
    }
    description
      "Grid spacing value.";
  }
}
