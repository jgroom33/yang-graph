module ciena-waveserver-typedefs {
  namespace "urn:ciena:params:xml:ns:yang:ciena-ws:ciena-waveserver-typedefs";
  prefix cienawstypes;

  import ciena-ui {
    prefix ui;
  }

  import yuma-ncx {
    prefix ncx;
  }

  organization
    "Ciena Corporation";
  contact
    "Web URL: http://www.ciena.com/
     Postal:  7035 Ridge Road
             Hanover, Maryland 21076
             U.S.A.
     Phone:   +1 800-921-1144
     Fax:     +1 410-694-5750";
  description
    "This YANG module defines Ciena's commonly used typedefs";

  revision 2023-06-22 {
    description
      "Added 'mixed-otn-ethernet-2 to the xcvr-service-profile table.";
    reference
      "Waveserver OS R2.5 user's guide.";
  }
  revision 2023-01-30 {
    description
      "Added 'xcvr-mode' enum values for lines for 107 bate rate.
       Added 'xcvr-type' enum value for CFP2-DCO and the associated 'xcvr-mode' enum values.
       Added 'line-fail-type' typedef.
       Add forward-error-correction-mode";
    reference
      "Waveserver OS R2.4 user's guide.";
  }
  revision 2021-06-11 {
    description
      "Added 'xcvr-mode' enum values for lines for 93.3, 90, 85 and 82 GBAUD, for 200 to 800G bit-rate and for -O and -E";
    reference
      "Waveserver OS R2.2 user's guide.";
  }
  revision 2021-04-09 {
    description
      "Added '4x100GE-ZR' enum value to 'xcvr-mode' typedef.
       Removed device-specific ranges from 'modem-frequency' and 'tx-power-lvl'
       typedefs to allow for dynamic range checks based on device capabilities.";
    reference
      "Waveserver OS R2.1 user's guide.";
  }
  revision 2020-03-18 {
    description
      "Added 'waveserver 5 chassis' enum value to 'chassis-type' typedef.
       Added 'WaveLogic 5e' and 'QSFP-DD' to 'xcvr-type' typedef.
       Added 'xcvr-mode' enum values for clients: '4x100GE', 'FOIC1.4', 'FOIC4.8'.
       Added 'typedef xcvr-service-profile'.
       Added 'typedef xcvr-firmware-state-enum'.
       Updated 'modem-frequency' range values for expanded C-Band capabilities.
       Updated the range for  typedef lanes-number.
       Added 'xcvr-mode' enum values for lines: '95-200-O' to '69.5-660-E'.";
    reference
      "Waveserver OS R2.0 user's guide.";
  }
  revision 2019-06-03 {
    description
      "Added 'protocol-specific' enum value to 'condition-type' typedef.";
    reference
      "Waveserver Ai R1.5 user's guide.";
  }
  revision 2019-03-29 {
    description
      "Added 'xcvr-type' enum values: 'SFP' and 'None'.
       Added 'xcvr-mode' enum values: '4x10GE', 'OCH', 'OTM', 'OSC', and 'OSC-Add-Drop'.
       Added typedef for 'chassis-type'.
       Added 'ipv6-prefix', 'ipv6-opt-prefix', 'ip-opt-prefix' typedefs.
       Updated 'modem-frequency' range values for expanded C-Band capabilities.
       Added rpc groupings 'rpc-output', 'rpc-log-upload-group', and 'rpc-oper-status-group'.";
    reference
      "Waveserver Ai R1.4 user's guide.";
  }
  revision 2018-08-23 {
    description
      "Added typedef for 'string-maxl-8'.
       Added typedefs for 'ipv6-address' and 'ip-address'.";
    reference
      "Waveserver Ai R1.3 user's guide.";
  }
  revision 2018-05-17 {
    description
      "Added 'xcvr-mode' enum values.
       Added 'supported-link-optimization-modes' bits typedef.
       Added 'squelch-traffic' mode to 'mismatch-fail-mode' enum.
       Added 'modem-class' and 'link-optimization-mode' types.
       Added 'ipv4-address', 'ipv4-prefix', 'ipv4-opt-prefix' typedefs.
       Updated range for 'tx-power-lvl' typedef.";
    reference
      "Waveserver Ai R1.2 user's guide.";
  }
  revision 2018-01-04 {
    description
      "Updated 'modem-frequency' range values for C-Band and L-Band capabilities.
       Added 'otn' enum value to 'conditioning-type' typedef.
       Removed unused OTUCn 'xcvr-mode' enum values and added OTL4.4/OTLC.4 support.
       Added 'ipaddr-or-hostname' typedef.";
    reference
      "Waveserver Ai R1.1 user's guide.";
  }
  revision 2017-09-05 {
    description
      "Waveserver Platform Data Model
       Migrated from Waveserver Classic R1.4 YANG model.
       Updated namespace to 'ciena-waveserver'.
       Added 'xcvr-mode' enum values.
       Added 'power-state' typedef.
       Renamed 'channels-number' typedef to 'lanes-number'.
       Removed 'xcvr-id', 'ptp-id', 'port-id' types; use string types instead.
       Added 'conditioning-type' and 'conditioning-holdoff' typedefs.
       Remove line-module-type-bits typedef.
       Added 'trace-mismatch-mode' and 'trace-mismatch-fail-mode'.
       Added 'restart-reason'.
       Removed several unused typedefs.";
    reference
      "Waveserver Ai R1.0 user's guide.";
  }

  typedef mac-string {
    type string {
      length "1..20";
    }
    description
      "MAC address string.";
  }

  typedef name-string {
    type string {
      length "1..32";
    }
    description
      "String type for object names used in Ciena defined modules. It must be a
       non empty string that is at most 32 characters long.";
  }

  typedef description-string {
    type string {
      length "0..128";
    }
    description
      "String type for description used in Ciena defined modules. Max length of
       128 characters, plus null.";
  }

  typedef on-off-enum {
    type enumeration {
      enum "off" {
        description
          "Off";
      }
      enum "on" {
        description
          "On";
      }
    }
    description
      "Off and On enum toggle used in Ciena defined modules.";
  }

  typedef power-state {
    type enumeration {
      enum "automatic" {
        description
          "Power state is automatic (on/normal).";
      }
      enum "shutdown" {
        description
          "Power state is shutdown (off/low-power-mode).";
      }
    }
    description
      "Power state automatic (on/normal) or shutdown (off/low-power-mode).";
  }

  typedef yes-no-enum {
    type enumeration {
      enum "no" {
        description
          "No";
      }
      enum "yes" {
        description
          "Yes";
      }
    }
    description
      "No and Yes enum toggle used in Ciena defined modules.";
  }

  typedef up-down-enum {
    type enumeration {
      enum "down" {
        description
          "Object is down/disabled/failed.";
      }
      enum "up" {
        description
          "Object is up/operational.";
      }
    }
    description
      "Down and Up enum toggle used in Ciena defined modules.";
  }

  typedef enabled-disabled-enum {
    type enumeration {
      enum "disabled" {
        description
          "Object or attribute is disabled.";
      }
      enum "enabled" {
        description
          "Object or attribute is enabled.";
      }
    }
    description
      "Enabled and Disabled enum toggle used in Ciena defined modules.";
  }

  typedef forward-error-correction-mode {
    type enumeration {
      enum "disabled" {
        description
          "FEC disabled";
      }
      enum "enabled" {
        description
          "FEC enabled";
      }
      enum "automatic" {
        description
          "System determines FEC settings";
      }
    }
    description
      "Forward error correction mode";
  }

  typedef yes-no-na-enum {
    type enumeration {
      enum "no" {
        description
          "No";
      }
      enum "yes" {
        description
          "Yes";
      }
      enum "not-applicable" {
        description
          "Not applicable";
      }
    }
    description
      "No and Yes enum toggle used in Ciena defined modules.";
  }

  typedef enabled-disabled-na-enum {
    type enumeration {
      enum "disabled" {
        description
          "Disabled";
      }
      enum "enabled" {
        description
          "Enabled";
      }
      enum "not-applicable" {
        description
          "Not applicable";
      }
    }
    description
      "Enabled, Disabled, and not-applicable enum used in Ciena defined modules.";
  }

  typedef wl-spacing {
    type enumeration {
      enum "50GHz" {
        description
          "50GHz wavelength spacing.";
      }
      enum "100GHz" {
        description
          "100GHz wavelength spacing.";
      }
      enum "200GHz" {
        description
          "200GHz wavelength spacing.";
      }
      enum "flex-grid" {
        description
          "Flex-grid wavelength spacing.";
      }
    }
    description
      "Wavelength spacing, 50GHz, 100GHz, 200GHz, or flex-grid. Only 'flex-grid'
       supported in Waveserver Ai R1.0.";
  }

  typedef decimal-3-dig {
    type decimal64 {
      fraction-digits 3;
      range "-2147483.0 .. 2147483.0";
    }
    description
      "Decimal value up to 3 digits.";
  }

  typedef decimal-2-dig-small {
    type decimal64 {
      fraction-digits 2;
      range "-30000.0 .. 30000.0";
    }
    description
      "Decimal value up to 2 digits.";
  }

  typedef decimal-2-dig {
    type decimal64 {
      fraction-digits 2;
      range "-21474836.0 .. 21474836.0";
    }
    description
      "Decimal value up to 2 digits.";
  }

  typedef decimal-1-dig {
    type decimal64 {
      fraction-digits 1;
      range "-214748364.0 .. 214748364.0";
    }
    description
      "Decimal value up to 1 digits.";
  }

  typedef string-sci {
    type string {
      length "0..32";
      pattern "[-+]?[0-9](\\.[0-9]+)?([eE][-+]?[0-9]+)?";
    }
    description
      "String in Scientific Notation format with a max length of 32 characters.";
  }

  typedef string-maxl-8 {
    type string {
      length "0..8";
    }
    description
      "Standard string that has a max length of 8 characters. Can be used for
       various nodes that may require string of this length.";
  }

  typedef string-maxl-15 {
    type string {
      length "0..15";
    }
    description
      "Standard string that has a max length of 15 characters. Can be used for
       various nodes that may require string of this length.";
  }

  typedef string-maxl-16 {
    type string {
      length "0..16";
    }
    description
      "Standard string that has a max length of 16 characters. Can be used for
       various nodes that may require string of this length.";
  }

  typedef string-maxl-32 {
    type string {
      length "0..32";
    }
    description
      "Standard string that has a max length of 32 characters. Can be used for
       various nodes that may require string of this length.";
  }

  typedef string-maxl-44 {
    type string {
      length "0..44";
    }
    description
      "Standard string that has a max length of 44 characters. Can be used for
       various nodes that may require string of this length.";
  }

  typedef string-maxl-50 {
    type string {
      length "0..50";
    }
    description
      "Standard string that has a max length of 50 characters. Can be used for
       various nodes that may require string of this length.";
  }

  typedef string-maxl-64 {
    type string {
      length "0..64";
    }
    description
      "Standard string that has a max length of 64 characters. Can be used for
       various nodes that may require string of this length.";
  }

  typedef string-maxl-128 {
    type string {
      length "0..128";
    }
    description
      "Standard string that has a max length of 128 characters. Can be used for
       various nodes that may require string of this length.";
  }

  typedef string-maxl-254 {
    type string {
      length "0..254";
    }
    description
      "Standard string that has a max length of 254 characters. Can be used for
       various nodes that may require string of this length.";
  }

  typedef string-maxl-256 {
    type string {
      length "0..256";
    }
    description
      "Standard string that has a max length of 256 characters. Can be used for
       various nodes that may require string of this length.";
  }

  typedef ipaddr-or-hostname {
    type string {
      length "1..63";
    }
    description
      "IP address or hostname string.";
  }

  typedef ip-address {
    type union {
      type ipv4-address;
      type ipv6-address;
      type string {
        pattern "Unresolved";
      }
    }
    description
      "An IP address type that supports both IPv4 and IPv6 formats.";
  }

  typedef ip-opt-prefix {
    type union {
      type ipv4-opt-prefix;
      type ipv6-opt-prefix;
      type string {
        pattern "Unresolved";
      }
    }
    description
      "An IP prefix type that supports both IPv4 and IPv6 formats.";
  }

  typedef ipv4-address {
    type string {
      length "0..16";
      pattern "(([0-9]|[1-9][0-9]|1[0-9][0-9]|2[0-4][0-9]|25[0-5])\\.){3}([0-9]|[1-9][0-9]|1[0-9][0-9]|2[0-4][0-9]|25[0-5])";
    }
    description
      "An IPv4 address represented in dotted decimal notation.";
  }

  typedef ipv4-prefix {
    type string {
      length "0..20";
      pattern "(([0-9]|[1-9][0-9]|1[0-9][0-9]|2[0-4][0-9]|25[0-5])\\.){3}([0-9]|[1-9][0-9]|1[0-9][0-9]|2[0-4][0-9]|25[0-5])/(([0-9])|([1-2][0-9])|(3[0-2]))";
    }
    description
      "An IPv4 address and prefix represented in dotted decimal notation
       followed by a slash and a prefix length, e.g. '192.168.1.2/24'.";
  }

  typedef ipv4-opt-prefix {
    type string {
      length "0..20";
      pattern "(([0-9]|[1-9][0-9]|1[0-9][0-9]|2[0-4][0-9]|25[0-5])\\.){3}([0-9]|[1-9][0-9]|1[0-9][0-9]|2[0-4][0-9]|25[0-5])(/(([0-9])|([1-2][0-9])|(3[0-2])))?";
    }
    description
      "A string type matching either the ipv4-address format or the
       ipv4-prefix format. That is, an IPv4 address in dotted decimal
       notation with an optional slash and prefix length.";
  }

  typedef ipv6-address {
    type string {
      pattern "[0-9a-fA-F:\\.]*";
    }
    description
      "An IPv6 address format.";
    reference
      "RFC 4291: IP Version 6 Addressing Architecture
       RFC 4007: IPv6 Scoped Address Architecture
       RFC 5952: A Recommendation for IPv6 Address Text
                 Representation";
  }

  typedef ipv6-prefix {
    type string {
      pattern "((:|[0-9a-fA-F]{0,4}):)([0-9a-fA-F]{0,4}:){0,5}((([0-9a-fA-F]{0,4}:)?(:|[0-9a-fA-F]{0,4}))|(((25[0-5]|2[0-4][0-9]|[01]?[0-9]?[0-9])\\.){3}(25[0-5]|2[0-4][0-9]|[01]?[0-9]?[0-9])))(/(([0-9])|([0-9]{2})|(1[0-1][0-9])|(12[0-8])))";
    }
    description
      "The ipv6-prefix type represents an IPv6 address prefix.
       The prefix length is given by the number following the
       slash character and must be less than or equal to 128.

       A prefix length value of n corresponds to an IP address
       mask that has n contiguous 1-bits from the most
       significant bit (MSB) and all other bits set to 0.

       The IPv6 address should have all bits that do not belong
       to the prefix set to zero.

       The canonical format of an IPv6 prefix has all bits of
       the IPv6 address set to zero that are not part of the
       IPv6 prefix.  Furthermore, the IPv6 address is represented
       as defined in Section 4 of RFC 5952.";
    reference
      "RFC 5952: A Recommendation for IPv6 Address Text
                 Representation";
  }

  typedef ipv6-opt-prefix {
    type string {
      pattern "((:|[0-9a-fA-F]{0,4}):)([0-9a-fA-F]{0,4}:){0,5}((([0-9a-fA-F]{0,4}:)?(:|[0-9a-fA-F]{0,4}))|(((25[0-5]|2[0-4][0-9]|[01]?[0-9]?[0-9])\\.){3}(25[0-5]|2[0-4][0-9]|[01]?[0-9]?[0-9])))(/(([0-9])|([0-9]{2})|(1[0-1][0-9])|(12[0-8])))?";
    }
    description
      "A string type matching either the ipv6-address format or the
       ipv6-prefix format. That is, an IPv6 address with an optional
       slash and prefix length.";
  }

  typedef port-name {
    type string {
      length "1..32";
    }
    description
      "A string representing a port interface name. Format is: '<slot>-<port>'
       or '<slot>-<majorport>.<minorport>'.";
  }

  typedef service-idx {
    type uint32 {
      range "0 .. 1000";
    }
    description
      "Service Index";
  }

  typedef service-domain-idx {
    type uint32 {
      range "0 .. 20";
    }
    description
      "Service Domain Index";
  }

  typedef chassis-type {
    type enumeration {
      enum "unknown chassis" {
        description
          "Chassis type is unknown.";
      }
      enum "waveserver chassis" {
        description
          "Waveserver WL3e Chassis.";
      }
      enum "waveserver ai chassis" {
        description
          "Waveserver Ai Chassis.";
      }
      enum "waveserver 5 chassis" {
        description
          "Waveserver 5 Chassis.";
      }
    }
    description
      "Type enum value of the chassis.";
  }

  typedef xcvr-firmware-state-enum {
    type enumeration {
      enum "unknown" {
        description
          "Unknown state.";
      }
      enum "idle" {
        description
          "Firmware is in idle state.";
      }
      enum "upgrading" {
        description
          "Firmware is in upgrading state.";
      }
      enum "failed" {
        description
          "Firmware is in failed state.";
      }
    }
    description
      "Define the enum for XCVR firmware states.";
  }

  typedef xcvr-type {
    type enumeration {
      enum "not-available" {
        value 0;
        description
          "XCVR type not available.";
      }
      enum "unsupported" {
        value 1;
        description
          "XCVR type unsupported.";
      }
      enum "QSFPplus" {
        value 2;
        description
          "XCVR type QSFP+; Quad Small Form-factor Pluggable capable of 40 Gb
           data transmission.";
      }
      enum "QSFP28" {
        value 3;
        description
          "XCVR type QSFP28; Quad Small Form-factor Pluggable capable of 100 Gb
           data transmission.";
      }
      enum "WaveLogic 3 Extreme" {
        value 4;
        description
          "XCVR type WL3e.";
      }
      enum "WaveLogic Ai" {
        value 5;
        description
          "XCVR type WLAi.";
      }
      enum "SFP" {
        value 6;
        description
          "XCVR type SFP; Small Form-Factor Pluggable capable of 1 GbE data
           transmission.";
      }
      enum "none" {
        value 7;
        description
          "Port has no XCVR type, meaning it represents a passive optical
           connector only. Applicable to OCH, OTM, and OSC-Add/Drop port types.";
      }
      enum "QSFP-DD" {
        value 8;
        description
          "XCVR type QSFP-DD; Double-Density Quad Small Form-factor Pluggable
           capable of up to 400 Gbps data transmission.";
      }
      enum "WaveLogic 5e" {
        value 9;
        description
          "XCVR type WL5e.";
      }
      enum "CFP2-DCO" {
        value 10;
        description
          "XCVR type CFP2-DCO.";
      }
    }
    description
      "Transceiver type.";
  }

  typedef xcvr-mode {
    type enumeration {
      enum "blank" {
        value 0;
        description
          "XCVR/slot is blank.";
      }
      enum "OCH" {
        value 1;
        description
          "Optical Channel port mode.";
      }
      enum "OTM" {
        value 2;
        description
          "Optical Multiplex port mode.";
      }
      enum "OSC" {
        value 3;
        description
          "Optical Supervisory Channel port mode.";
      }
      enum "OSC-Add-Drop" {
        value 4;
        description
          "Optical Supervisory Channel Add/Drop port mode.";
      }
      enum "10GE" {
        value 10;
        description
          "XCVR mode 10 Gigabit Ethernet.";
      }
      enum "4x10GE" {
        value 11;
        description
          "XCVR mode 4 x 10 Gigabit Ethernet.";
      }
      enum "40GE" {
        value 40;
        description
          "XCVR mode 40 Gigabit Ethernet.";
      }
      enum "100GE" {
        value 100;
        description
          "XCVR mode 100 Gigabit Ethernet.";
      }
      enum "400GE" {
        value 400;
        description
          "XCVR mode 400 Gigabit Ethernet.";
      }
      enum "400GE-ZR" {
        value 401;
        description
          "XCVR mode 400ZR/CFEC with 400 Gigabit Ethernet.";
      }
      enum "400GE-ZR+" {
        value 402;
        description
          "XCVR mode 400ZR+/OFEC with 400 Gigabit Ethernet.";
      }
      enum "4x100GE" {
        value 4100;
        description
          "XCVR mode 4x100 Gigabit Ethernet or OTN";
      }
      enum "4x100GE-ZR" {
        value 4101;
        description
          "XCVR mode 400ZR/CFEC with 100 Gigabit Ethernet.";
      }
      enum "4x100GE-ZR+" {
        value 4102;
        description
          "XCVR mode 400ZR+/OFEC with 100 Gigabit Ethernet.";
      }
      enum "OTL4.4" {
        value 58044;
        description
          "XCVR mode OTL4.4.";
      }
      enum "OTLC.4" {
        value 58104;
        description
          "XCVR mode OTLC.4.";
      }
      enum "FOIC1.4" {
        value 60014;
        description
          "XCVR mode FOIC1.4. Line passthrough mode only(regen)";
      }
      enum "FOIC4.8" {
        value 60048;
        description
          "XCVR mode FOIC4.8. FR4/DR4/DR4+/etc. based on plug capability.
           Line passthrough mode only(regen).";
      }
      enum "35-100" {
        value 350100;
        description
          "XCVR mode 35Gbaud, 100Gbps.";
      }
      enum "35-150" {
        value 350150;
        description
          "XCVR mode 35Gbaud, 150Gbps.";
      }
      enum "35-200" {
        value 350200;
        description
          "XCVR mode 35Gbaud, 200Gbps.";
      }
      enum "35-250" {
        value 350250;
        description
          "XCVR mode 35Gbaud, 250Gbps.";
      }
      enum "56-100" {
        value 560100;
        description
          "XCVR mode 56Gbaud, 100Gbps.";
      }
      enum "56-150" {
        value 560150;
        description
          "XCVR mode 56Gbaud, 150Gbps.";
      }
      enum "56-200" {
        value 560200;
        description
          "XCVR mode 56Gbaud, 200Gbps.";
      }
      enum "56-250" {
        value 560250;
        description
          "XCVR mode 56Gbaud, 250Gbps.";
      }
      enum "56-300" {
        value 560300;
        description
          "XCVR mode 56Gbaud, 300Gbps.";
      }
      enum "56-350" {
        value 560350;
        description
          "XCVR mode 56Gbaud, 350Gbps.";
      }
      enum "56-400" {
        value 560400;
        description
          "XCVR mode 56Gbaud, 400Gbps.";
      }
      enum "70-300-O" {
        value 7003000;
        description
          "XCVR mode WL5n based pluggable, 70Gbaud, 300Gbps, OTN.";
      }
      enum "70-400-O" {
        value 7004000;
        description
          "XCVR mode WL5n based pluggable, 70Gbaud, 400Gbps, OTN.";
      }
      enum "70-400-E" {
        value 7004001;
        description
          "XCVR mode WL5n based pluggable, 70Gbaud, 400Gbps, Ethernet.";
      }
      enum "65-300-E" {
        value 6503001;
        description
          "XCVR mode WL5n based pluggable, 65Gbaud, 300Gbps, Ethernet.";
      }
      enum "65-400-E" {
        value 6504001;
        description
          "XCVR mode WL5n based pluggable, 65Gbaud, 400Gbps, Ethernet.";
      }
      enum "63-200-O" {
        value 6302000;
        description
          "XCVR mode WL5n based pluggable, 63Gbaud, 200Gbps, OTN.";
      }
      enum "63-400-O" {
        value 6304000;
        description
          "XCVR mode WL5n based pluggable, 63Gbaud, 400Gbps, OTN.";
      }
      enum "60-400-E-ZR" {
        value 60040010;
        description
          "XCVR mode WL5n based pluggable, 60Gbaud, 400Gbps, Ethernet w/ CFEC.";
      }
      enum "60-400-E-ZR+" {
        value 60040011;
        description
          "XCVR mode WL5n based pluggable, 60Gbaud, 400Gbps, Ethernet w/ OFEC.";
      }
      enum "60-200-E" {
        value 6002001;
        description
          "XCVR mode WL5n based pluggable, 60Gbaud, 200Gbps, Ethernet.";
      }
      enum "58-200-O" {
        value 5802000;
        description
          "XCVR mode WL5n based pluggable, 58Gbaud, 200Gbps, OTN.";
      }
      enum "35-200-O" {
        value 3502000;
        description
          "XCVR mode WL5n based pluggable, 35Gbaud, 200Gbps, OTN.";
      }
      enum "31.5-100-O" {
        value 31501000;
        description
          "XCVR mode WL5n based pluggable, 31.5Gbaud, 100Gbps, OTN.";
      }
      enum "31.5-200-O" {
        value 31502000;
        description
          "XCVR mode WL5n based pluggable, 31.5Gbaud, 200Gbps, OTN.";
      }
      enum "95-200-O" {
        value 9502000;
        description
          "XCVR mode 95Gbaud, 200Gbps, OTN.";
      }
      enum "95-250-O" {
        value 9502500;
        description
          "XCVR mode 95Gbaud, 250Gbps, OTN.";
      }
      enum "95-300-O" {
        value 9503000;
        description
          "XCVR mode 95Gbaud, 300Gbps, OTN.";
      }
      enum "95-350-O" {
        value 9503500;
        description
          "XCVR mode 95Gbaud, 350Gbps, OTN.";
      }
      enum "95-400-O" {
        value 9504000;
        description
          "XCVR mode 95Gbaud, 400Gbps, OTN.";
      }
      enum "95-450-O" {
        value 9504500;
        description
          "XCVR mode 95Gbaud, 450Gbps, OTN.";
      }
      enum "95-500-O" {
        value 9505000;
        description
          "XCVR mode 95Gbaud, 500Gbps, OTN.";
      }
      enum "95-550-O" {
        value 9505500;
        description
          "XCVR mode 95Gbaud, 550Gbps, OTN.";
      }
      enum "95-600-O" {
        value 9506000;
        description
          "XCVR mode 95Gbaud, 600Gbps, OTN.";
      }
      enum "95-650-O" {
        value 9506500;
        description
          "XCVR mode 95Gbaud, 650Gbps, OTN.";
      }
      enum "95-700-O" {
        value 9507000;
        description
          "XCVR mode 95Gbaud, 700Gbps, OTN.";
      }
      enum "95-750-O" {
        value 9507500;
        description
          "XCVR mode 95Gbaud, 750Gbps, OTN.";
      }
      enum "95-800-O" {
        value 9508000;
        description
          "XCVR mode 95Gbaud, 800Gbps, OTN.";
      }
      enum "95-200-E" {
        value 9502001;
        description
          "XCVR mode 95Gbaud, 200Gbps, Ethernet.";
      }
      enum "95-250-E" {
        value 9502501;
        description
          "XCVR mode 95Gbaud, 250Gbps, Ethernet.";
      }
      enum "95-300-E" {
        value 9503001;
        description
          "XCVR mode 95Gbaud, 300Gbps, Ethernet.";
      }
      enum "95-350-E" {
        value 9503501;
        description
          "XCVR mode 95Gbaud, 350Gbps, Ethernet.";
      }
      enum "95-400-E" {
        value 9504001;
        description
          "XCVR mode 95Gbaud, 400Gbps, Ethernet.";
      }
      enum "95-450-E" {
        value 9504501;
        description
          "XCVR mode 95Gbaud, 450Gbps, Ethernet.";
      }
      enum "95-500-E" {
        value 9505001;
        description
          "XCVR mode 95Gbaud, 400Gbps, Ethernet.";
      }
      enum "95-550-E" {
        value 9505501;
        description
          "XCVR mode 95Gbaud, 550Gbps, Ethernet.";
      }
      enum "95-600-E" {
        value 9506001;
        description
          "XCVR mode 95Gbaud, 500Gbps, Ethernet.";
      }
      enum "95-650-E" {
        value 9506501;
        description
          "XCVR mode 95Gbaud, 650Gbps, Ethernet.";
      }
      enum "95-700-E" {
        value 9507001;
        description
          "XCVR mode 95Gbaud, 700Gbps, Ethernet.";
      }
      enum "95-750-E" {
        value 9507501;
        description
          "XCVR mode 95Gbaud, 750Gbps, Ethernet.";
      }
      enum "95-800-E" {
        value 9508001;
        description
          "XCVR mode 95Gbaud, 800Gbps, Ethernet.";
      }
      enum "91.6-200-O" {
        value 91602000;
        description
          "XCVR mode 91.6Gbaud, 200Gbps, OTN.";
      }
      enum "91.6-250-O" {
        value 91602500;
        description
          "XCVR mode 91.6Gbaud, 250Gbps, OTN.";
      }
      enum "91.6-300-O" {
        value 91603000;
        description
          "XCVR mode 91.6Gbaud, 300Gbps, OTN.";
      }
      enum "91.6-350-O" {
        value 91603500;
        description
          "XCVR mode 91.6Gbaud, 350Gbps, OTN.";
      }
      enum "91.6-400-O" {
        value 91604000;
        description
          "XCVR mode 91.6Gbaud, 400Gbps, OTN.";
      }
      enum "91.6-450-O" {
        value 91604500;
        description
          "XCVR mode 91.6Gbaud, 450Gbps, OTN.";
      }
      enum "91.6-500-O" {
        value 91605000;
        description
          "XCVR mode 91.6Gbaud, 500Gbps, OTN.";
      }
      enum "91.6-550-O" {
        value 91605500;
        description
          "XCVR mode 91.6Gbaud, 550Gbps, OTN.";
      }
      enum "91.6-600-O" {
        value 91606000;
        description
          "XCVR mode 91.6Gbaud, 600Gbps, OTN.";
      }
      enum "91.6-650-O" {
        value 91606500;
        description
          "XCVR mode 91.6Gbaud, 650Gbps, OTN.";
      }
      enum "91.6-700-O" {
        value 91607000;
        description
          "XCVR mode 91.6Gbaud, 700Gbps, OTN.";
      }
      enum "91.6-750-O" {
        value 91607500;
        description
          "XCVR mode 91.6Gbaud, 750Gbps, OTN.";
      }
      enum "91.6-800-O" {
        value 91608000;
        description
          "XCVR mode 91.6Gbaud, 800Gbps, OTN.";
      }
      enum "91.6-200-E" {
        value 91602001;
        description
          "XCVR mode 91.6Gbaud, 200Gbps, Ethernet.";
      }
      enum "91.6-250-E" {
        value 91602501;
        description
          "XCVR mode 91.6Gbaud, 250Gbps, Ethernet.";
      }
      enum "91.6-300-E" {
        value 91603001;
        description
          "XCVR mode 91.6Gbaud, 300Gbps, Ethernet.";
      }
      enum "91.6-350-E" {
        value 91603501;
        description
          "XCVR mode 91.6Gbaud, 350Gbps, Ethernet.";
      }
      enum "91.6-400-E" {
        value 91604001;
        description
          "XCVR mode 91.6Gbaud, 400Gbps, Ethernet.";
      }
      enum "91.6-450-E" {
        value 91604501;
        description
          "XCVR mode 91.6Gbaud, 450Gbps, Ethernet.";
      }
      enum "91.6-500-E" {
        value 91605001;
        description
          "XCVR mode 91.6Gbaud, 500Gbps, Ethernet.";
      }
      enum "91.6-550-E" {
        value 91605501;
        description
          "XCVR mode 91.6Gbaud, 550Gbps, Ethernet.";
      }
      enum "91.6-600-E" {
        value 91606001;
        description
          "XCVR mode 91.6Gbaud, 600Gbps, Ethernet.";
      }
      enum "91.6-650-E" {
        value 91606501;
        description
          "XCVR mode 91.6Gbaud, 650Gbps, Ethernet.";
      }
      enum "91.6-700-E" {
        value 91607001;
        description
          "XCVR mode 91.6Gbaud, 700Gbps, Ethernet.";
      }
      enum "91.6-750-E" {
        value 91607501;
        description
          "XCVR mode 91.6Gbaud, 750Gbps, Ethernet.";
      }
      enum "91.6-800-E" {
        value 91608001;
        description
          "XCVR mode 91.6Gbaud, 800Gbps, Ethernet.";
      }
      enum "89.3-200-O" {
        value 89302000;
        description
          "XCVR mode 89.3Gbaud, 200Gbps, OTN.";
      }
      enum "89.3-250-O" {
        value 89302500;
        description
          "XCVR mode 89.3Gbaud, 250Gbps, OTN.";
      }
      enum "89.3-300-O" {
        value 89303000;
        description
          "XCVR mode 89.3Gbaud, 300Gbps, OTN.";
      }
      enum "89.3-350-O" {
        value 89303500;
        description
          "XCVR mode 89.3Gbaud, 350Gbps, OTN.";
      }
      enum "89.3-400-O" {
        value 89304000;
        description
          "XCVR mode 89.3Gbaud, 400Gbps, OTN.";
      }
      enum "89.3-450-O" {
        value 89304500;
        description
          "XCVR mode 89.3Gbaud, 450Gbps, OTN.";
      }
      enum "89.3-500-O" {
        value 89305000;
        description
          "XCVR mode 89.3Gbaud, 500Gbps, OTN.";
      }
      enum "89.3-550-O" {
        value 89305500;
        description
          "XCVR mode 89.3Gbaud, 550Gbps, OTN.";
      }
      enum "89.3-600-O" {
        value 89306000;
        description
          "XCVR mode 89.3Gbaud, 600Gbps, OTN.";
      }
      enum "89.3-650-O" {
        value 89306500;
        description
          "XCVR mode 89.3Gbaud, 650Gbps, OTN.";
      }
      enum "89.3-700-O" {
        value 89307000;
        description
          "XCVR mode 89.3Gbaud, 700Gbps, OTN.";
      }
      enum "89.3-750-O" {
        value 89307500;
        description
          "XCVR mode 89.3Gbaud, 750Gbps, OTN.";
      }
      enum "89.3-800-O" {
        value 89308000;
        description
          "XCVR mode 89.3Gbaud, 800Gbps, OTN.";
      }
      enum "89.3-200-E" {
        value 89302001;
        description
          "XCVR mode 89.3Gbaud, 200Gbps, Ethernet.";
      }
      enum "89.3-250-E" {
        value 89302501;
        description
          "XCVR mode 89.3Gbaud, 250Gbps, Ethernet.";
      }
      enum "89.3-300-E" {
        value 89303001;
        description
          "XCVR mode 89.3Gbaud, 300Gbps, Ethernet.";
      }
      enum "89.3-350-E" {
        value 89303501;
        description
          "XCVR mode 89.3Gbaud, 350Gbps, Ethernet.";
      }
      enum "89.3-400-E" {
        value 89304001;
        description
          "XCVR mode 89.3Gbaud, 400Gbps, Ethernet.";
      }
      enum "89.3-450-E" {
        value 89304501;
        description
          "XCVR mode 89.3Gbaud, 450Gbps, Ethernet.";
      }
      enum "89.3-500-E" {
        value 89305001;
        description
          "XCVR mode 89.3Gbaud, 500Gbps, Ethernet.";
      }
      enum "89.3-550-E" {
        value 89305501;
        description
          "XCVR mode 89.3Gbaud, 550Gbps, Ethernet.";
      }
      enum "89.3-600-E" {
        value 89306001;
        description
          "XCVR mode 89.3Gbaud, 600Gbps, Ethernet.";
      }
      enum "89.3-650-E" {
        value 89306501;
        description
          "XCVR mode 89.3Gbaud, 650Gbps, Ethernet.";
      }
      enum "89.3-700-E" {
        value 89307001;
        description
          "XCVR mode 89.3Gbaud, 700Gbps, Ethernet.";
      }
      enum "89.3-750-E" {
        value 89307501;
        description
          "XCVR mode 89.3Gbaud, 750Gbps, Ethernet.";
      }
      enum "89.3-800-E" {
        value 89308001;
        description
          "XCVR mode 89.3Gbaud, 800Gbps, Ethernet.";
      }
      enum "71.3-200-O" {
        value 71302000;
        description
          "XCVR mode 71.3Gbaud, 200Gbps, OTN.";
      }
      enum "71.3-250-O" {
        value 71302500;
        description
          "XCVR mode 71.3Gbaud, 250Gbps, OTN.";
      }
      enum "71.3-300-O" {
        value 71303000;
        description
          "XCVR mode 71.3Gbaud, 300Gbps, OTN.";
      }
      enum "71.3-350-O" {
        value 71303500;
        description
          "XCVR mode 71.3Gbaud, 350Gbps, OTN.";
      }
      enum "71.3-400-O" {
        value 71304000;
        description
          "XCVR mode 71.3Gbaud, 400Gbps, OTN.";
      }
      enum "71.3-450-O" {
        value 71304500;
        description
          "XCVR mode 71.3Gbaud, 450Gbps, OTN.";
      }
      enum "71.3-500-O" {
        value 71305000;
        description
          "XCVR mode 71.3Gbaud, 500Gbps, OTN.";
      }
      enum "71.3-550-O" {
        value 71305500;
        description
          "XCVR mode 71.3Gbaud, 550Gbps, OTN.";
      }
      enum "71.3-600-O" {
        value 71306000;
        description
          "XCVR mode 71.3Gbaud, 600Gbps, OTN.";
      }
      enum "71.3-200-E" {
        value 71302001;
        description
          "XCVR mode 71.3Gbaud, 200Gbps, Ethernet.";
      }
      enum "71.3-250-E" {
        value 71302501;
        description
          "XCVR mode 71.3Gbaud, 250Gbps, Ethernet.";
      }
      enum "71.3-300-E" {
        value 71303001;
        description
          "XCVR mode 71.3Gbaud, 300Gbps, Ethernet.";
      }
      enum "71.3-350-E" {
        value 71303501;
        description
          "XCVR mode 71.3Gbaud, 350Gbps, Ethernet.";
      }
      enum "71.3-400-E" {
        value 71304001;
        description
          "XCVR mode 71.3Gbaud, 400Gbps, Ethernet.";
      }
      enum "71.3-450-E" {
        value 71304501;
        description
          "XCVR mode 71.3Gbaud, 450Gbps, Ethernet.";
      }
      enum "71.3-500-E" {
        value 71305001;
        description
          "XCVR mode 71.3Gbaud, 500Gbps, Ethernet.";
      }
      enum "71.3-550-E" {
        value 71305501;
        description
          "XCVR mode 71.3Gbaud, 550Gbps, Ethernet.";
      }
      enum "71.3-600-E" {
        value 71306001;
        description
          "XCVR mode 71.3Gbaud, 600Gbps, Ethernet.";
      }
      enum "69.5-200-O" {
        value 69502000;
        description
          "XCVR mode 69.5Gbaud, 200Gbps, OTN.";
      }
      enum "69.5-250-O" {
        value 69502500;
        description
          "XCVR mode 69.5Gbaud, 250Gbps, OTN.";
      }
      enum "69.5-300-O" {
        value 69503000;
        description
          "XCVR mode 69.5Gbaud, 300Gbps, OTN.";
      }
      enum "69.5-350-O" {
        value 69503500;
        description
          "XCVR mode 69.5Gbaud, 350Gbps, OTN.";
      }
      enum "69.5-400-O" {
        value 69504000;
        description
          "XCVR mode 69.5Gbaud, 400Gbps, OTN.";
      }
      enum "69.5-450-O" {
        value 69504500;
        description
          "XCVR mode 69.5Gbaud, 450Gbps, OTN.";
      }
      enum "69.5-500-O" {
        value 69505000;
        description
          "XCVR mode 69.5Gbaud, 500Gbps, OTN.";
      }
      enum "69.5-550-O" {
        value 69505500;
        description
          "XCVR mode 69.5Gbaud, 550Gbps, OTN.";
      }
      enum "69.5-600-O" {
        value 69506000;
        description
          "XCVR mode 69.5Gbaud, 600Gbps, OTN.";
      }
      enum "69.5-200-E" {
        value 69502001;
        description
          "XCVR mode 69.5Gbaud, 200Gbps, Ethernet.";
      }
      enum "69.5-250-E" {
        value 69502501;
        description
          "XCVR mode 69.5Gbaud, 250Gbps, Ethernet.";
      }
      enum "69.5-300-E" {
        value 69503001;
        description
          "XCVR mode 69.5Gbaud, 300Gbps, Ethernet.";
      }
      enum "69.5-350-E" {
        value 69503501;
        description
          "XCVR mode 69.5Gbaud, 350Gbps, Ethernet.";
      }
      enum "69.5-400-E" {
        value 69504001;
        description
          "XCVR mode 69.5Gbaud, 400Gbps, Ethernet.";
      }
      enum "69.5-450-E" {
        value 69504501;
        description
          "XCVR mode 69.5Gbaud, 450Gbps, Ethernet.";
      }
      enum "69.5-500-E" {
        value 69505001;
        description
          "XCVR mode 69.5Gbaud, 500Gbps, Ethernet.";
      }
      enum "69.5-550-E" {
        value 69505501;
        description
          "XCVR mode 69.5Gbaud, 550Gbps, Ethernet.";
      }
      enum "69.5-600-E" {
        value 69506001;
        description
          "XCVR mode 69.5Gbaud, 600Gbps, Ethernet.";
      }
      enum "93.3-200-O" {
        value 93302000;
        description
          "XCVR mode 93.3Gbaud, 200Gbps, OTN.";
      }
      enum "93.3-250-O" {
        value 93302500;
        description
          "XCVR mode 93.3Gbaud, 250Gbps, OTN.";
      }
      enum "93.3-300-O" {
        value 93303000;
        description
          "XCVR mode 93.3Gbaud, 300Gbps, OTN.";
      }
      enum "93.3-350-O" {
        value 93303500;
        description
          "XCVR mode 93.3Gbaud, 350Gbps, OTN.";
      }
      enum "93.3-400-O" {
        value 93304000;
        description
          "XCVR mode 93.3Gbaud, 400Gbps, OTN.";
      }
      enum "93.3-450-O" {
        value 93304500;
        description
          "XCVR mode 93.3Gbaud, 450Gbps, OTN.";
      }
      enum "93.3-500-O" {
        value 93305000;
        description
          "XCVR mode 93.3Gbaud, 500Gbps, OTN.";
      }
      enum "93.3-550-O" {
        value 93305500;
        description
          "XCVR mode 93.3Gbaud, 550Gbps, OTN.";
      }
      enum "93.3-600-O" {
        value 93306000;
        description
          "XCVR mode 93.3Gbaud, 600Gbps, OTN.";
      }
      enum "93.3-650-O" {
        value 93306500;
        description
          "XCVR mode 93.3Gbaud, 650Gbps, OTN.";
      }
      enum "93.3-700-O" {
        value 93307000;
        description
          "XCVR mode 93.3Gbaud, 700Gbps, OTN.";
      }
      enum "93.3-750-O" {
        value 93307500;
        description
          "XCVR mode 93.3Gbaud, 750Gbps, OTN.";
      }
      enum "93.3-800-O" {
        value 93308000;
        description
          "XCVR mode 93.3Gbaud, 800Gbps, OTN.";
      }
      enum "93.3-200-E" {
        value 93302001;
        description
          "XCVR mode 93.3Gbaud, 200Gbps, Ethernet.";
      }
      enum "93.3-250-E" {
        value 93302501;
        description
          "XCVR mode 93.3Gbaud, 250Gbps, Ethernet.";
      }
      enum "93.3-300-E" {
        value 93303001;
        description
          "XCVR mode 93.3Gbaud, 300Gbps, Ethernet.";
      }
      enum "93.3-350-E" {
        value 93303501;
        description
          "XCVR mode 93.3Gbaud, 350Gbps, Ethernet.";
      }
      enum "93.3-400-E" {
        value 93304001;
        description
          "XCVR mode 93.3Gbaud, 400Gbps, Ethernet.";
      }
      enum "93.3-450-E" {
        value 93304501;
        description
          "XCVR mode 93.3Gbaud, 450Gbps, Ethernet.";
      }
      enum "93.3-500-E" {
        value 93305001;
        description
          "XCVR mode 93.3Gbaud, 500Gbps, Ethernet.";
      }
      enum "93.3-550-E" {
        value 93305501;
        description
          "XCVR mode 93.3Gbaud, 550Gbps, Ethernet.";
      }
      enum "93.3-600-E" {
        value 93306001;
        description
          "XCVR mode 93.3Gbaud, 600Gbps, Ethernet.";
      }
      enum "93.3-650-E" {
        value 93306501;
        description
          "XCVR mode 93.3Gbaud, 650Gbps, Ethernet.";
      }
      enum "93.3-700-E" {
        value 93307001;
        description
          "XCVR mode 93.3Gbaud, 700Gbps, Ethernet.";
      }
      enum "93.3-750-E" {
        value 93307501;
        description
          "XCVR mode 93.3Gbaud, 750Gbps, Ethernet.";
      }
      enum "93.3-800-E" {
        value 93308001;
        description
          "XCVR mode 93.3Gbaud, 800Gbps, Ethernet.";
      }
      enum "90-200-O" {
        value 90002000;
        description
          "XCVR mode 90Gbaud, 200Gbps, OTN.";
      }
      enum "90-250-O" {
        value 90002500;
        description
          "XCVR mode 90Gbaud, 250Gbps, OTN.";
      }
      enum "90-300-O" {
        value 90003000;
        description
          "XCVR mode 90Gbaud, 300Gbps, OTN.";
      }
      enum "90-350-O" {
        value 90003500;
        description
          "XCVR mode 90Gbaud, 350Gbps, OTN.";
      }
      enum "90-400-O" {
        value 90004000;
        description
          "XCVR mode 90Gbaud, 400Gbps, OTN.";
      }
      enum "90-450-O" {
        value 90004500;
        description
          "XCVR mode 90Gbaud, 450Gbps, OTN.";
      }
      enum "90-500-O" {
        value 90005000;
        description
          "XCVR mode 90Gbaud, 500Gbps, OTN.";
      }
      enum "90-550-O" {
        value 90005500;
        description
          "XCVR mode 90Gbaud, 550Gbps, OTN.";
      }
      enum "90-600-O" {
        value 90006000;
        description
          "XCVR mode 90Gbaud, 600Gbps, OTN.";
      }
      enum "90-650-O" {
        value 90006500;
        description
          "XCVR mode 90Gbaud, 650Gbps, OTN.";
      }
      enum "90-700-O" {
        value 90007000;
        description
          "XCVR mode 90Gbaud, 700Gbps, OTN.";
      }
      enum "90-750-O" {
        value 90007500;
        description
          "XCVR mode 90Gbaud, 750Gbps, OTN.";
      }
      enum "90-800-O" {
        value 90008000;
        description
          "XCVR mode 90Gbaud, 800Gbps, OTN.";
      }
      enum "90-200-E" {
        value 90002001;
        description
          "XCVR mode 90Gbaud, 200Gbps, Ethernet.";
      }
      enum "90-250-E" {
        value 90002501;
        description
          "XCVR mode 90Gbaud, 250Gbps, Ethernet.";
      }
      enum "90-300-E" {
        value 90003001;
        description
          "XCVR mode 90Gbaud, 300Gbps, Ethernet.";
      }
      enum "90-350-E" {
        value 90003501;
        description
          "XCVR mode 90Gbaud, 350Gbps, Ethernet.";
      }
      enum "90-400-E" {
        value 90004001;
        description
          "XCVR mode 90Gbaud, 400Gbps, Ethernet.";
      }
      enum "90-450-E" {
        value 90004501;
        description
          "XCVR mode 90Gbaud, 450Gbps, Ethernet.";
      }
      enum "90-500-E" {
        value 90005001;
        description
          "XCVR mode 90Gbaud, 500Gbps, Ethernet.";
      }
      enum "90-550-E" {
        value 90005501;
        description
          "XCVR mode 90Gbaud, 550Gbps, Ethernet.";
      }
      enum "90-600-E" {
        value 90006001;
        description
          "XCVR mode 90Gbaud, 600Gbps, Ethernet.";
      }
      enum "90-650-E" {
        value 90006501;
        description
          "XCVR mode 90Gbaud, 650Gbps, Ethernet.";
      }
      enum "90-700-E" {
        value 90007001;
        description
          "XCVR mode 90Gbaud, 700Gbps, Ethernet.";
      }
      enum "90-750-E" {
        value 90007501;
        description
          "XCVR mode 90Gbaud, 750Gbps, Ethernet.";
      }
      enum "90-800-E" {
        value 90008001;
        description
          "XCVR mode 90Gbaud, 800Gbps, Ethernet.";
      }
      enum "85-200-O" {
        value 85002000;
        description
          "XCVR mode 85Gbaud, 200Gbps, OTN.";
      }
      enum "85-250-O" {
        value 85002500;
        description
          "XCVR mode 85Gbaud, 250Gbps, OTN.";
      }
      enum "85-300-O" {
        value 85003000;
        description
          "XCVR mode 85Gbaud, 300Gbps, OTN.";
      }
      enum "85-350-O" {
        value 85003500;
        description
          "XCVR mode 85Gbaud, 350Gbps, OTN.";
      }
      enum "85-400-O" {
        value 85004000;
        description
          "XCVR mode 85Gbaud, 400Gbps, OTN.";
      }
      enum "85-450-O" {
        value 85004500;
        description
          "XCVR mode 85Gbaud, 450Gbps, OTN.";
      }
      enum "85-500-O" {
        value 85005000;
        description
          "XCVR mode 85Gbaud, 500Gbps, OTN.";
      }
      enum "85-550-O" {
        value 85005500;
        description
          "XCVR mode 85Gbaud, 550Gbps, OTN.";
      }
      enum "85-600-O" {
        value 85006000;
        description
          "XCVR mode 85Gbaud, 600Gbps, OTN.";
      }
      enum "85-650-O" {
        value 85006500;
        description
          "XCVR mode 85Gbaud, 650Gbps, OTN.";
      }
      enum "85-700-O" {
        value 85007000;
        description
          "XCVR mode 85Gbaud, 700Gbps, OTN.";
      }
      enum "85-750-O" {
        value 85007500;
        description
          "XCVR mode 85Gbaud, 750Gbps, OTN.";
      }
      enum "85-800-O" {
        value 85008000;
        description
          "XCVR mode 85Gbaud, 800Gbps, OTN.";
      }
      enum "85-200-E" {
        value 85002001;
        description
          "XCVR mode 85Gbaud, 200Gbps, Ethernet.";
      }
      enum "85-250-E" {
        value 85002501;
        description
          "XCVR mode 85Gbaud, 250Gbps, Ethernet.";
      }
      enum "85-300-E" {
        value 85003001;
        description
          "XCVR mode 85Gbaud, 300Gbps, Ethernet.";
      }
      enum "85-350-E" {
        value 85003501;
        description
          "XCVR mode 85Gbaud, 350Gbps, Ethernet.";
      }
      enum "85-400-E" {
        value 85004001;
        description
          "XCVR mode 85Gbaud, 400Gbps, Ethernet.";
      }
      enum "85-450-E" {
        value 85004501;
        description
          "XCVR mode 85Gbaud, 450Gbps, Ethernet.";
      }
      enum "85-500-E" {
        value 85005001;
        description
          "XCVR mode 85Gbaud, 500Gbps, Ethernet.";
      }
      enum "85-550-E" {
        value 85005501;
        description
          "XCVR mode 85Gbaud, 550Gbps, Ethernet.";
      }
      enum "85-600-E" {
        value 85006001;
        description
          "XCVR mode 85Gbaud, 600Gbps, Ethernet.";
      }
      enum "85-650-E" {
        value 85006501;
        description
          "XCVR mode 85Gbaud, 650Gbps, Ethernet.";
      }
      enum "85-700-E" {
        value 85007001;
        description
          "XCVR mode 85Gbaud, 700Gbps, Ethernet.";
      }
      enum "85-750-E" {
        value 85007501;
        description
          "XCVR mode 85Gbaud, 750Gbps, Ethernet.";
      }
      enum "85-800-E" {
        value 85008001;
        description
          "XCVR mode 85Gbaud, 800Gbps, Ethernet.";
      }
      enum "82-200-O" {
        value 82002000;
        description
          "XCVR mode 82Gbaud, 200Gbps, OTN.";
      }
      enum "82-250-O" {
        value 82002500;
        description
          "XCVR mode 82Gbaud, 250Gbps, OTN.";
      }
      enum "82-300-O" {
        value 82003000;
        description
          "XCVR mode 82Gbaud, 300Gbps, OTN.";
      }
      enum "82-350-O" {
        value 82003500;
        description
          "XCVR mode 82Gbaud, 350Gbps, OTN.";
      }
      enum "82-400-O" {
        value 82004000;
        description
          "XCVR mode 82Gbaud, 400Gbps, OTN.";
      }
      enum "82-450-O" {
        value 82004500;
        description
          "XCVR mode 82Gbaud, 450Gbps, OTN.";
      }
      enum "82-500-O" {
        value 82005000;
        description
          "XCVR mode 82Gbaud, 500Gbps, OTN.";
      }
      enum "82-550-O" {
        value 82005500;
        description
          "XCVR mode 82Gbaud, 550Gbps, OTN.";
      }
      enum "82-600-O" {
        value 82006000;
        description
          "XCVR mode 82Gbaud, 600Gbps, OTN.";
      }
      enum "82-650-O" {
        value 82006500;
        description
          "XCVR mode 82Gbaud, 650Gbps, OTN.";
      }
      enum "82-700-O" {
        value 82007000;
        description
          "XCVR mode 82Gbaud, 700Gbps, OTN.";
      }
      enum "82-750-O" {
        value 82007500;
        description
          "XCVR mode 82Gbaud, 750Gbps, OTN.";
      }
      enum "82-800-O" {
        value 82008000;
        description
          "XCVR mode 82Gbaud, 800Gbps, OTN.";
      }
      enum "82-200-E" {
        value 82002001;
        description
          "XCVR mode 82Gbaud, 200Gbps, Ethernet.";
      }
      enum "82-250-E" {
        value 82002501;
        description
          "XCVR mode 82Gbaud, 250Gbps, Ethernet.";
      }
      enum "82-300-E" {
        value 82003001;
        description
          "XCVR mode 82Gbaud, 300Gbps, Ethernet.";
      }
      enum "82-350-E" {
        value 82003501;
        description
          "XCVR mode 82Gbaud, 350Gbps, Ethernet.";
      }
      enum "82-400-E" {
        value 82004001;
        description
          "XCVR mode 82Gbaud, 400Gbps, Ethernet.";
      }
      enum "82-450-E" {
        value 82004501;
        description
          "XCVR mode 82Gbaud, 450Gbps, Ethernet.";
      }
      enum "82-500-E" {
        value 82005001;
        description
          "XCVR mode 82Gbaud, 500Gbps, Ethernet.";
      }
      enum "82-550-E" {
        value 82005501;
        description
          "XCVR mode 82Gbaud, 550Gbps, Ethernet.";
      }
      enum "82-600-E" {
        value 82006001;
        description
          "XCVR mode 82Gbaud, 600Gbps, Ethernet.";
      }
      enum "82-650-E" {
        value 82006501;
        description
          "XCVR mode 82Gbaud, 650Gbps, Ethernet.";
      }
      enum "82-700-E" {
        value 82007001;
        description
          "XCVR mode 82Gbaud, 700Gbps, Ethernet.";
      }
      enum "82-750-E" {
        value 82007501;
        description
          "XCVR mode 82Gbaud, 750Gbps, Ethernet.";
      }
      enum "82-800-E" {
        value 82008001;
        description
          "XCVR mode 82Gbaud, 800Gbps, Ethernet.";
      }
      enum "107-200-O" {
        value 1070200;
        description
          "Line XCVR mode 107GBaud, 200Gbps, OTN Transcoding.";
      }
      enum "107-200-E" {
        value 1070201;
        description
          "Line XCVR mode 107GBaud, 200Gbps, Ethernet Transcoding.";
      }
      enum "107-250-O" {
        value 1070250;
        description
          "Line XCVR mode 107GBaud, 250Gbps, OTN Transcoding.";
      }
      enum "107-250-E" {
        value 1070251;
        description
          "Line XCVR mode 107GBaud, 250Gbps, Ethernet Transcoding.";
      }
      enum "107-300-O" {
        value 1070300;
        description
          "Line XCVR mode 107GBaud, 300Gbps, OTN Transcoding.";
      }
      enum "107-300-E" {
        value 1070301;
        description
          "Line XCVR mode 107GBaud, 300Gbps, Ethernet Transcoding.";
      }
      enum "107-350-O" {
        value 1070350;
        description
          "Line XCVR mode 107GBaud, 350Gbps, OTN Transcoding.";
      }
      enum "107-350-E" {
        value 1070351;
        description
          "Line XCVR mode 107GBaud, 350Gbps, Ethernet Transcoding.";
      }
      enum "107-400-O" {
        value 1070400;
        description
          "Line XCVR mode 107GBaud, 400Gbps, OTN Transcoding.";
      }
      enum "107-400-E" {
        value 1070401;
        description
          "Line XCVR mode 107GBaud, 400Gbps, Ethernet Transcoding.";
      }
      enum "107-450-O" {
        value 1070450;
        description
          "Line XCVR mode 107GBaud, 450Gbps, OTN Transcoding.";
      }
      enum "107-450-E" {
        value 1070451;
        description
          "Line XCVR mode 107GBaud, 450Gbps, Ethernet Transcoding.";
      }
      enum "107-500-O" {
        value 1070500;
        description
          "Line XCVR mode 107GBaud, 500Gbps, OTN Transcoding.";
      }
      enum "107-500-E" {
        value 1070501;
        description
          "Line XCVR mode 107GBaud, 500Gbps, Ethernet Transcoding.";
      }
      enum "107-550-O" {
        value 1070550;
        description
          "Line XCVR mode 107GBaud, 550Gbps, OTN Transcoding.";
      }
      enum "107-550-E" {
        value 1070551;
        description
          "Line XCVR mode 107GBaud, 550Gbps, Ethernet Transcoding.";
      }
      enum "107-600-O" {
        value 1070600;
        description
          "Line XCVR mode 107GBaud, 600Gbps, OTN Transcoding.";
      }
      enum "107-600-E" {
        value 1070601;
        description
          "Line XCVR mode 107GBaud, 600Gbps, Ethernet Transcoding.";
      }
      enum "107-650-O" {
        value 1070650;
        description
          "Line XCVR mode 107GBaud, 650Gbps, OTN Transcoding.";
      }
      enum "107-650-E" {
        value 1070651;
        description
          "Line XCVR mode 107GBaud, 650Gbps, Ethernet Transcoding.";
      }
      enum "107-700-O" {
        value 1070700;
        description
          "Line XCVR mode 107GBaud, 700Gbps, OTN Transcoding.";
      }
      enum "107-700-E" {
        value 1070701;
        description
          "Line XCVR mode 107GBaud, 700Gbps, Ethernet Transcoding.";
      }
      enum "107-750-O" {
        value 1070750;
        description
          "Line XCVR mode 107GBaud, 750Gbps, OTN Transcoding.";
      }
      enum "107-750-E" {
        value 1070751;
        description
          "Line XCVR mode 107GBaud, 750Gbps, Ethernet Transcoding.";
      }
      enum "107-800-O" {
        value 1070800;
        description
          "Line XCVR mode 107GBaud, 800Gbps, OTN Transcoding.";
      }
      enum "107-800-E" {
        value 1070801;
        description
          "Line XCVR mode 107GBaud, 800Gbps, Ethernet Transcoding.";
      }
    }
    description
      "Transceiver mode.";
  }

  typedef xcvr-service-profile {
    type enumeration {
      enum "none" {
        description
          "No service profile.";
      }
      enum "100GE" {
        description
          "100GE service profile.";
      }
      enum "400GE" {
        description
          "400GE service profile.";
      }
      enum "4x100GE" {
        description
          "4x100GE service profile.";
      }
      enum "mixed-ethernet" {
        description
          "Mixed Ethernet service profile.";
      }
      enum "mixed-otn-ethernet" {
        description
          "Mixed OTN Ethernet service profile.";
      }
      enum "mixed-otn-ethernet-2" {
        description
          "Mixed OTN Ethernet-2 service profile.";
      }
      enum "FOIC1.4" {
        description
          "FOIC1.4 service profile.";
      }
      enum "FOIC4.8" {
        description
          "FOIC4.8 service profile.";
      }
    }
    description
      "Transceiver service profile.";
  }

  typedef line-sys-enum {
    type enumeration {
      enum "coloured" {
        description
          "Line system coloured.";
      }
      enum "colourless" {
        description
          "Line system colourless.";
      }
      enum "contentionless" {
        description
          "Line system contentionless.";
      }
      enum "cs-coloured" {
        description
          "Line system cs-coloured.";
      }
      enum "cs-colourless" {
        description
          "Line system cs-colourless.";
      }
    }
    description
      "Line system type.";
  }

  typedef lanes-number {
    type uint16 {
      range "0 .. 8";
    }
    description
      "Lane number common type, lane range is defined from 0 to 4.";
  }

  typedef connector-type-desc-enum {
    type enumeration {
      enum "Unknown or unspecified" {
        value 0;
        description
          "Unknown or unspecified.";
      }
      enum "SC - Subscriber Connector" {
        value 1;
        description
          "SC - Subscriber Connector.";
      }
      enum "Fibre Channel Style 1 copper connector" {
        value 2;
        description
          "Fibre Channel Style 1 copper connector.";
      }
      enum "Fibre Channel Style 2 copper connector" {
        value 3;
        description
          "Fibre Channel Style 2 copper connector.";
      }
      enum "BNC/TNC - Bayonet/Threaded Neill-Concelman" {
        value 4;
        description
          "BNC/TNC - Bayonet/Threaded Neill-Concelman.";
      }
      enum "Fibre Channel coax headers" {
        value 5;
        description
          "Fibre Channel coax headers.";
      }
      enum "Fiber Jack" {
        value 6;
        description
          "Fiber Jack.";
      }
      enum "LC - Lucent Connector" {
        value 7;
        description
          "LC - Lucent Connector.";
      }
      enum "MT-RJ - Mechanical Transfer - Registered Jack" {
        value 8;
        description
          "MT-RJ - Mechanical Transfer - Registered Jack.";
      }
      enum "MU - Multiple Optical" {
        value 9;
        description
          "MU - Multiple Optical.";
      }
      enum "SG" {
        value 10;
        description
          "SG.";
      }
      enum "Optical Pigtail" {
        value 11;
        description
          "Optical Pigtail.";
      }
      enum "MPO 1x12 - Multifiber Parallel Optic" {
        value 12;
        description
          "MPO 1x12 - Multifiber Parallel Optic.";
      }
      enum "MPO 2x16" {
        value 13;
        description
          "MPO 2x16.";
      }
      enum "HSSDC II - High Speed Serial Data Connector" {
        value 32;
        description
          "HSSDC II - High Speed Serial Data Connector.";
      }
      enum "Copper pigtail" {
        value 33;
        description
          "Copper pigtail.";
      }
      enum "RJ45 - Registered Jack" {
        value 34;
        description
          "RJ45 - Registered Jack.";
      }
      enum "No separable connector" {
        value 35;
        description
          "No separable connector.";
      }
      enum "MXC 2x16" {
        value 36;
        description
          "MXC 2x16.";
      }
    }
    description
      "Human readable description of Vendor's connector type byte value.";
    reference
      "SFF-8024, table 4-3";
  }

  typedef modem-frequency {
    type decimal64 {
      fraction-digits 1;
      range "0.0 .. max";
    }
    units "GHz";
    description
      "Modem frequency, in GHz. 0.0 indicates unprovisioned (default) value. L-Band
       range is 186087.5 - 190956.2 GHz, and C-Band range is 191250.0 - 196125.0 GHz.
       Some devices may support values outside of these ranges. Range checks are
       enforced dynamically based on device capabilities.";
  }

  typedef modem-class {
    type enumeration {
      enum "terrestrial" {
        description
          "Terrestrial modem class.";
      }
      enum "submarine" {
        description
          "Submarine modem class.";
      }
      enum "unavailable" {
        description
          "Modem class is unavailable.";
      }
    }
    description
      "The modem class type, terrestrial or submarine.";
  }

  typedef link-optimization-mode {
    type enumeration {
      enum "standard" {
        description
          "Standard Mode - Default setting which provides best SNR performance.";
      }
      enum "snr-tolerant" {
        description
          "SNR Tolerant Mode - Recommended for applications that want to
           achieve maximum SNR tolerance while still providing reasonable
           polarization tracking speed and PDL tolerance.";
      }
      enum "fast-tracking" {
        description
          "Fast Tracking Mode - Recommended for applications that want to
           maximize SOP tracking.";
      }
      enum "spectral-efficiency" {
        description
          "Spectral Efficiency Mode - Recommended for applications that want
           to maximize spectral efficiency by minimizing spectral signal width.";
      }
      enum "latency" {
        description
          "Low Latency Mode - Recommended for applications that want to
           minimize transmission latency.";
      }
      enum "foreign" {
        description
          "Foreign Line Mode - Recommended for applications that require the
           transmitted signal to be be recognized/controlled by a foreign line
           system.";
      }
      enum "narrow" {
        description
          "Narrow Channel Mode - Recommended for applications that want to
           achieve maximum SNR tolerance over heavily filtered optical link.";
      }
      enum "non-linear" {
        description
          "Non-Linear Channel Mode - Recommended for applications that want
           to achieve maximum SNR tolerance on a non-linear fiber link.";
      }
      enum "reserved-1" {
        description
          "Reserved Mode 1.";
      }
      enum "reserved-2" {
        description
          "Reserved Mode 2.";
      }
      enum "reserved-3" {
        description
          "Reserved Mode 3.";
      }
      enum "custom" {
        description
          "Custom Link Optimization Mode.";
      }
      enum "unavailable" {
        description
          "Link Optimization Mode is unavailable.";
      }
    }
    description
      "Link Optimization Modes for the WaveLogic modems.";
  }

  typedef supported-link-optimization-modes {
    type bits {
      bit standard {
        description
          "Supports standard link-optimization-mode.";
      }
      bit snr-tolerant {
        description
          "Supports snr-tolerant link-optimization-mode.";
      }
      bit fast-tracking {
        description
          "Supports fast-tracking link-optimization-mode.";
      }
      bit spectral-efficiency {
        description
          "Supports spectral-efficiency link-optimization-mode.";
      }
      bit latency {
        description
          "Supports latency link-optimization-mode.";
      }
      bit foreign {
        description
          "Supports foreign link-optimization-mode.";
      }
      bit narrow {
        description
          "Supports narrow link-optimization-mode.";
      }
      bit non-linear {
        description
          "Supports non-linear link-optimization-mode.";
      }
      bit reserved-1 {
        description
          "Supports reserved-1 link-optimization-mode.";
      }
      bit reserved-2 {
        description
          "Supports reserved-2 link-optimization-mode.";
      }
      bit reserved-3 {
        description
          "Supports reserved-3 link-optimization-mode.";
      }
      bit custom {
        description
          "Supports custom link-optimization-mode.";
      }
    }
    description
      "Type definition for supported link-optimization-mode values for PTPs
       associated with modem XCVR objects.";
  }

  typedef tx-power-lvl {
    type decimal64 {
      fraction-digits 1;
    }
    units "dBm";
    description
      "Modem Tx Power Level.";
  }

  typedef module-type-enum {
    type enumeration {
      enum "unknown" {
        description
          "Module type unknown.";
      }
      enum "integrated" {
        description
          "Module type integrated.";
      }
      enum "field-replaceable" {
        description
          "Module type field-replaceable.";
      }
    }
    description
      "Module type enum.";
  }

  typedef module-type-bits {
    type bits {
      bit integrated {
        position 0;
        description
          "Module type integrated.";
      }
      bit field-replaceable {
        position 1;
        description
          "Module type field-replaceable.";
      }
    }
    description
      "Module type bits.";
  }

  typedef restart-reason {
    type enumeration {
      enum "unknown" {
        description
          "Unknown restart reason.";
      }
      enum "user-warm" {
        description
          "User-initiated warm restart.";
      }
      enum "user-cold" {
        description
          "User-initiated cold restart.";
      }
      enum "system-warm" {
        description
          "System-initiated warm restart.";
      }
      enum "system-cold" {
        description
          "System-initiated cold restart.";
      }
      enum "power-on" {
        description
          "Device inserted or powered on.";
      }
    }
    description
      "Chassis/Module last restart reason.";
  }

  typedef conditioning-type {
    type enumeration {
      enum "none" {
        value 0;
        description
          "No consequent action, if applicable for the specified port.";
      }
      enum "laser-off" {
        value 1;
        description
          "Disable the transmitter consequent action, if applicable for the
           specified port.";
      }
      enum "ethernet" {
        value 2;
        description
          "Ethernet Local Fault consequent action. Only applicable for Ethernet
           client ports. For system default-settings, this value maps to the
           generic 'protocol-specific' enum value.";
      }
      enum "otn" {
        value 3;
        description
          "Standard OTN consequent action as defined in ITU-T G.798. Only
           applicable for OTN client ports. For system default-settings, this
           value maps to the generic 'protocol-specific' enum value.";
      }
      enum "protocol-specific" {
        value 4;
        description
          "Protocol-specific default value, based on the port type. For
           Ethernet client ports, this maps to 'ethernet', and for OTN client
           ports, this mapes to 'otn'.";
      }
    }
    description
      "Egress UNI port consequent action for an EPL service to be applied on a
       far-end ingress UNI failure or network failure.";
  }

  typedef conditioning-holdoff {
    type int16 {
      range "0|10|20|30|40|50|60|70|80|90|100|200|300|400|500|600|700|800|900|1000";
    }
    units "ms";
    description
      "Number of milliseconds to delay Egress UNI port consequent action for an
       EPL service.";
  }

  typedef trace-mismatch-mode {
    type enumeration {
      enum "operator-only" {
        value 1;
        description
          "Trace mismatch detection criteria includes operator-specific trace
           string only. Other fields are ignored.";
      }
      enum "sapi" {
        value 2;
        description
          "Trace mismatch detection criteria includes source access point
           identifier (SAPI) trace string only. Other fields are ignored.";
      }
      enum "dapi" {
        value 3;
        description
          "Trace mismatch detection criteria includes destination access point
           identifier (DAPI) trace string only. Other fields are ignored.";
      }
      enum "sapi-and-dapi" {
        value 4;
        description
          "Trace mismatch detection criteria includes SAPI and DAPI strings. A
           mismatch of either of these fields will result in TTI mismatch. The
           operator specific field is ignored.";
      }
    }
    description
      "The trail trace identifier (TTI) mismatch mode, indicating which fields of
       the TTI overhead are used for trace mismatch detection.";
  }

  typedef trace-mismatch-fail-mode {
    type enumeration {
      enum "none" {
        description
          "TTI mismatch detection is disable or ignored. Do not raise an alarm on
           TTI mismatch condition.";
      }
      enum "alarm-only" {
        description
          "Raise an alarm when TTI mismatch occurs, but do not squelch traffic.";
      }
      enum "squelch-traffic" {
        description
          "Squelch the traffic via signal conditioning when TTI mismatch occurs.";
      }
    }
    description
      "The trail trace identifier (TTI) mismatch failure mode. When TTI mismatch
       condition occurs, this indicates the consequent action taken, e.g. whether
       or not to raise an alarm.";
  }

  typedef line-fail-type {
    type enumeration {
      enum "path-unidirectional" {
        description
          "Default value. path-unidirectional defects contribute to SSF";
      }
      enum "unidirectional" {
        description
          "Unidirectional defects contribute to SSF";
      }
      enum "path-bidirectional" {
        description
          "Path-bidirectional defects contribute to SSF";
      }
    }
    description
      "Indicates defects that contribute to SSF";
  }

  grouping rpc-output {
    description
      "RPC output properties.";
    leaf return-code {
      type uint32;
      description
        "return code: 0 is success; non-zero is failure";
    }

    leaf return-string {
      type string-maxl-254;
      description
        "Return code description";
    }
  }

  grouping rpc-log-upload-group {
    description
      "Parameters to set when uploading test results.";
    leaf url {
      ui:ui-name "Url";
      type string-maxl-254;
      description
        "The URL specifying the remote location and filename to upload the logfile.
         Formats: SCP/TFTP/FTP/SFTP/HTTP/HTTPS
         Example for node's auto-generated filename:  'scp://<uid>:<pwd>@<ip-address>/<path>/'.
         Example for user-defined filename: 'scp://<uid>:<pwd>@<ip-address>/<path>/<filename>'.";
    }

    leaf login-id {
      ui:ui-name "Login ID";
      type string-maxl-32;
      description
        "The username to login to the server. Not required if username is given in url.";
    }

    leaf password {
      ui:ui-name "Password";
      ncx:password;
      type string-maxl-128;
      description
        "The password. Not required if password is given in url.";
    }
  }

  grouping rpc-oper-status-group {
    description
      "Operation Status of a test";
    leaf oper-status {
      type uint8;
      description
        "Enum value of the Operational status of the test.";
    }

    leaf oper-status-string {
      type string-maxl-32;
      description
        "Description of the operational status of the test.";
    }
  }
}
