module ciena-pro-types {
  namespace "urn:ciena:params:xml:ns:yang:ciena-pro-types";
  prefix pro-types;

  import ciena-common-version {
    prefix ciena-common-version;
  }

  import ietf-yang-types {
    prefix ietf-yang-types;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena common objects.";

  revision 2022-03-29 {
    ciena-common-version:version "version" {
      ciena-common-version:string "1.4.1";
    }
    description
      "Move forced-shutoff grouping from pro-amp to pro-types.";
  }
  revision 2021-09-30 {
    ciena-common-version:version "version" {
      ciena-common-version:string "1.4.0";
    }
    description
      "Add hw-resolution type.";
  }
  revision 2021-05-18 {
    ciena-common-version:version "version" {
      ciena-common-version:string "1.3.1";
    }
    description
      "Add voltage type.";
  }
  revision 2021-02-24 {
    ciena-common-version:version "version" {
      ciena-common-version:string "1.3.0";
    }
    description
      "Add restart reason enumeration.";
  }
  revision 2020-12-14 {
    ciena-common-version:version "version" {
      ciena-common-version:string "1.2.0";
    }
    description
      "Add platform type common types.";
  }
  revision 2020-11-17 {
    ciena-common-version:version "version" {
      ciena-common-version:string "1.1.0";
    }
    description
      "Add a grouping for baseline values.";
  }
  revision 2020-08-01 {
    ciena-common-version:version "version" {
      ciena-common-version:string "1.0.0";
    }
    description
      "Initial version";
  }

  identity platform-type {
    description
      "This identity describes the platform type for the local or neighbour node.";
  }

  identity ciena-6500 {
    base platform-type;
    description
      "Ciena 6500 platform type";
  }

  identity ciena-5400 {
    base platform-type;
    description
      "Ciena 5400 platform type";
  }

  identity ciena-8700 {
    base platform-type;
    description
      "Ciena 8700 platform type";
  }

  identity ciena-waveserver {
    base platform-type;
    description
      "Ciena Waveserver platform type";
  }

  identity ciena-rls {
    base platform-type;
    description
      "Ciena RLS platform type";
  }

  typedef pec-code {
    type string {
      length "8..16";
    }
  }

  typedef site {
    type uint16 {
      range "0..65535";
    }
  }

  typedef object-name {
    type string {
      length "1..32";
    }
  }

  typedef restart-type {
    type enumeration {
      enum "warm" {
        value 1;
      }
      enum "cold" {
        value 2;
      }
    }
    description
      "Restart type";
  }

  typedef restart-reason {
    type enumeration {
      enum "unknown" {
        description
          "Unknown restart reason.";
      }
      enum "user-warm" {
        description
          "User-initiated warm restart.";
      }
      enum "user-cold" {
        description
          "User-initiated cold restart.";
      }
      enum "system-warm" {
        description
          "System-initiated warm restart.";
      }
      enum "system-cold" {
        description
          "System-initiated cold restart.";
      }
      enum "power-on" {
        description
          "Device inserted or powered on.";
      }
    }
    description
      "Chassis/Module last restart reason.";
  }

  typedef votage-V-1-precision {
    type decimal64 {
      fraction-digits 1;
    }
    units "V";
  }

  typedef hw-resolution {
    type enumeration {
      enum "high";
      enum "medium";
      enum "coarse";
    }
    description
      "Hardware resolution of the device.";
  }

  grouping admin-state {
    leaf admin-state {
      type enumeration {
        enum "Enabled" {
          value 1;
          description
            "Resource is Enabled.";
        }
        enum "Disabled" {
          value 2;
          description
            "Resource is Disabled.";
        }
        enum "Unassigned" {
          value 3;
          description
            "Resource is Unassigned.";
        }
      }
      description
        "Resource administrative state.";
    }
  }

  grouping operational-state {
    leaf operational-state {
      type enumeration {
        enum "uninstalled" {
          description
            "Resource is not present.";
        }
        enum "normal" {
          description
            "Resource is up/operational.";
        }
        enum "faulted" {
          description
            "Resource is in a failed/faulted state.";
        }
      }
      description
        "Resource operational state.";
    }
  }

  grouping baseline {
    leaf timestamp {
      type ietf-yang-types:date-and-time;
      description
        "The timestamp of the baseline";
    }

    leaf value {
      type decimal64 {
        fraction-digits 1;
      }
      description
        "Baseline value being set.";
    }
  }

  grouping forced-shutoff {
    leaf forced-shutoff {
      type enumeration {
        enum "Enabled" {
          value 2;
        }
        enum "Disabled" {
          value 1;
        }
      }
      default "Enabled";
      description
        "Forced Shutoff State";
    }
  }
}
