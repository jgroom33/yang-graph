module ciena-waveserver-pm {
  namespace "urn:ciena:params:xml:ns:yang:ciena-ws:ciena-waveserver-pm";
  prefix pm;

  import yuma-ncx {
    prefix ncx;
  }

  import ciena-waveserver-typedefs {
    prefix cienawstypes;
  }

  import ciena-ui {
    prefix ui;
  }

  organization
    "Ciena Corporation";
  contact
    "Web URL: http://www.ciena.com/
     Postal:  7035 Ridge Road
            Hanover, Maryland 21076
            U.S.A.
     Phone:   +1 800-921-1144
     Fax:     +1 410-694-5750";
  description
    "This module defines performance monitoring data for the Waveserver.";

  revision 2023-08-28 {
    description
      "Added PM modem stats applicable to CMIS XCVR mode.";
    reference
      "Waveserver OS R2.5 User guide.";
  }
  revision 2022-06-06 {
    description
      "Added new 'pm-interface-type' value 'protection'.
       Added new 'pm-profile-type' value 'protection-group'.
       Added grouping 'pm-pg-stats-group'.
       Added list 'protection-group-performance-instances'.
       Added new enum 'protection' to leaf 'interface-type' for the 'waveserver-pm-tca-admin-state-set-interface' RPC.";
    reference
      "Waveserver OS R2.4 user's guide.";
  }
  revision 2022-03-21 {
    description
      "Add new leaf 'profile-type' to the 'auto-created' container.
       Add new GCM counts: errored-seconds, far-end/errored-seconds and far-end/severely-errored-seconds and
       Deprecated 1 GCM count: error-count";
    reference
      "Waveserver OS R2.3.1 user's guide.";
  }
  revision 2021-09-21 {
    description
      "Add new modem counts: snr-ase, snr-tnle, esnr-delta, carrier-frequency-offset & error-vector-magnitude.
       Added a new leaf untimed-read-and-clear to global-config.";
    reference
      "Waveserver OS R2.2 user's guide.";
  }
  revision 2021-05-25 {
    description
      "Updated the description for input leafs bin-type and profile-type in rpc waveserver-pm-clear-interface.
       Removed deprecated persistence-state container.
       Removed obsolete frame-error-count and frame-error-count-seconds counters from fec-error container.
       Added lane-specific symbol-error-count stats to the fec-layer container.
       Updated timestamp date/time format descriptions.";
    reference
      "Waveserver OS R2.1 user's guide.";
  }
  revision 2020-03-09 {
    description
      "Changed description of container esnr in grouping pm-modem-stats-group
       from Electrical to Effective.
       Updated 'max-elements' to '8' for 'list optical-power'.";
    reference
      "Waveserver OS R2.0 user's guide.";
  }
  revision 2019-09-18 {
    description
      "Added support for Cycle slip indicator and SNR External count.
       Added support for PM TCA thresholds and baseline values.
       Added OTDR support to Photonics profile.
       Added rpc 'waveserver-pm-tca-admin-state-set-interface'.";
    reference
      "Waveserver Ai R1.5 user's guide.";
  }
  revision 2019-01-15 {
    description
      "Added 'aggregate-power' container to the optical power PM profile.
       Added new 'pm-profile-type' value 'photonics'.
       Updated 'pm-counter-percent-group' counters to 3-digit decimal precision.
       Added rpc 'waveserver-pm-clear-all'.
       Added typedef pm-bin-type.
       Updated 'pm-interface-type' enum values to { ptp | port | channel | slot }.";
    reference
      "Waveserver Ai R1.4 user's guide.";
  }
  revision 2018-07-30 {
    description
      "Updated counter type for 'dgd' counters from integer to decimal.
       Added 'grouping pm-gcm-stats-group'.
       Added 'list encryption-gcm-performance-instances'.
       Updated 'pm-profile-type' enum values to { optical-power | modem-performance |
                  otu-performance | odu-performance | ethernet-performance |
                  encryption-gcm-performance }.
       Added 'q-factor-standard-deviation' counter to PTP modem performance instances.";
    reference
      "Waveserver Ai R1.3 user's guide.";
  }
  revision 2018-06-27 {
    description
      "Obsoleted 'frame-error-count' and 'frame-error-count-second'.
       Updated counter type for 'frame-error-ratio' to use exponential notation.
       Added FEC 'uncorrected-second' counter to PTP modem performance instances.
       Added ESNR, OSNR, and chromatic-dispersion min/max/avg counters to
         PTP modem performance instances.
       Added ncx:user-write to the instances lists.";
    reference
      "Waveserver Ai R1.2 user's guide.";
  }
  revision 2018-01-16 {
    description
      "Added DGD max/avg and PDL max/avg PM counters to PTP modem performance instances.
       Updated Valid range for history bin-numbers are defined.";
    reference
      "Waveserver Ai R1.1 user's guide.";
  }
  revision 2017-09-18 {
    description
      "Waveserver Platform Data Model
       Migrated from Waveserver Classic R1.4 YANG model.
       Updated namespace to 'ciena-waveserver'.
       Update 'pm-interface-type' enum values to { ptp | port | channel }.
       Updated 'pm-profile-type' enum values to { optical-power | modem-performance |
                          otu-performance | odu-performance | ethernet-performance }.
       Removed obsolete 'mac-layer' containers.
       Removed 'instance-type' leafs and typedef.
       Removed 'pm-bin-state' leafs and typedef.
       Removed 'actual' from power-counts grouping.
       Removed 'post-fec-bit-error-rate' leafs.
       Removed 'alignment' from 'instance-properties' grouping.
       Restructured pm bin and instance data into nested groupings.
       Changed pm counters from leafs to containers with 'value', 'invalid-data-flag', and 'supported' leafs for each.
       Updated several counter attributes to match the Waveserver Ai data model.
       Removed 'current-bin-id' from pm instance state container.
       Removed 'bin-number' from the current bin id containers, only needed for history bins list.
       Removed 'persistence-interval' and 'persistence-storage-location' from 'global-config' container.";
    reference
      "Waveserver Ai R1.0 user's guide.";
  }

  typedef pm-configuration-mode {
    type enumeration {
      enum "unknown" {
        description
          "Unknown PM instance configuration mode.";
      }
      enum "auto-created" {
        description
          "PM instance is auto-created (default).";
      }
      enum "user-created" {
        description
          "PM instance is user-created.";
      }
    }
    description
      "PM configuration mode.";
  }

  typedef pm-interface-type {
    type enumeration {
      enum "ptp" {
        description
          "Associated interface is a PTP.";
      }
      enum "port" {
        description
          "Associated interface is an Ethernet or OTN port.";
      }
      enum "channel" {
        description
          "Associated interface is an ODU channel.";
      }
      enum "slot" {
        description
          "Associated interface is line module.";
      }
      enum "protection" {
        description
          "Associated interface is a protection group.";
      }
    }
    description
      "PM interface type. The object type on which the PMs are being collected/reported.";
  }

  typedef pm-profile-type {
    type enumeration {
      enum "optical-power" {
        description
          "PTP Optical Power PM profile type.";
      }
      enum "modem-performance" {
        description
          "PTP Modem PM profile type.";
      }
      enum "otu-performance" {
        description
          "Port OTU PM profile type.";
      }
      enum "odu-performance" {
        description
          "Port/Channel ODU profile type.";
      }
      enum "ethernet-performance" {
        description
          "Port Ethernet PM profile type.";
      }
      enum "encryption-gcm-performance" {
        description
          "Port Ethernet PM profile type.";
      }
      enum "photonics" {
        description
          "PTP Photonics PM profile type.";
      }
      enum "protection-group" {
        description
          "Protection-Group profile type.";
      }
    }
    description
      "PM profile type.";
  }

  typedef pm-bin-type {
    type enumeration {
      enum "15-min" {
        description
          "Identifies the 15-min current bin only.";
      }
      enum "24-hr" {
        description
          "Identifies the 24-hr current bin only.";
      }
      enum "untimed" {
        description
          "Identifies the untimed bin only.";
      }
      enum "history" {
        description
          "Identifies all historical 15-min and 24-hour bins.";
      }
      enum "all" {
        description
          "Identifies all current and historical bins.";
      }
    }
    description
      "PM bin type.";
  }

  typedef tca-notification-type {
    type enumeration {
      enum "summary-event" {
        description
          "TCA generates summary events.";
      }
      enum "summary-alarm" {
        description
          "TCA generates summary alarms.";
      }
      enum "event" {
        description
          "TCA generates events against interface/bin.";
      }
      enum "alarm" {
        description
          "TCA generates alarms against interface/bin.";
      }
    }
    description
      "TCA notification type.";
  }

  grouping pm-instance-id-container {
    description
      "Grouping for PM instance id container and attributes.";
    container id {
      ui:ui-name "Instance Id";
      config false;
      description
        "PM instance identification.";
      leaf instance-id {
        ui:ui-name "PM Instance Id";
        type uint32;
        description
          "ID of the PM instance.";
      }

      leaf profile-type {
        ui:ui-name "PM Profile Type";
        type pm-profile-type;
        description
          "The PM profile type.";
      }
    }
  }

  grouping pm-instance-state-container {
    description
      "Grouping for PM instance state container and attributes.";
    container state {
      ui:ui-name "Instance State";
      description
        "PM instance state.";
      leaf admin-state {
        ui:ui-name "Admin State";
        type cienawstypes:enabled-disabled-enum;
        description
          "The configured administrative state of the port.";
      }

      leaf tca-admin-state {
        ui:ui-name "TCA Admin State";
        type cienawstypes:enabled-disabled-enum;
        description
          "The configured TCA administrative state for this PM instance.";
      }

      leaf operational-state {
        ui:ui-name "Operational State";
        type cienawstypes:enabled-disabled-enum;
        config false;
        description
          "The operational state of the PM instance.";
      }

      leaf collection-start-date-time {
        ui:ui-name "Collection Start Date and Time";
        type cienawstypes:string-maxl-64;
        config false;
        description
          "The PM stats collection starting date and time, in 'YYYY-MM-DDTHH:MM:SS[+|-]hh:mm'
           format, or omitted if not applicable or unavailable.

           The string format follows IETF yang date-and-time specifications, compliant
           with RFC-6991. The base date and time portion of the string represents
           Coordinated Universal Time (UTC), and a non-zero hh:mm offset suffix indicates the
           system-configured local timezone offset at the time the event was recorded, and not
           necessarily when it was retrieved.

           When system timezone is set to UTC or no time-offset value is provisioned,
           the '+00:00' suffix will be used to indicate UTC time with no local offset.";
        reference
          "RFC 3339: Date and Time on the Internet: Timestamps
           RFC 6991: Common Yang Data Types";
      }

      leaf collection-end-date-time {
        ui:ui-name "Collection End Date and Time";
        type cienawstypes:string-maxl-64;
        config false;
        description
          "The PM stats collection ending date and time, in 'YYYY-MM-DDTHH:MM:SS[+|-]hh:mm'
           format, or omitted if not applicable or unavailable.

           The string format follows IETF yang date-and-time specifications, compliant
           with RFC-6991. The base date and time portion of the string represents
           Coordinated Universal Time (UTC), and a non-zero hh:mm offset suffix indicates the
           system-configured local timezone offset at the time the event was recorded, and not
           necessarily when it was retrieved.

           When system timezone is set to UTC or no time-offset value is provisioned,
           the '+00:00' suffix will be used to indicate UTC time with no local offset.";
        reference
          "RFC 3339: Date and Time on the Internet: Timestamps
           RFC 6991: Common Yang Data Types";
      }
    }
  }

  grouping pm-instance-properties-container {
    description
      "Grouping for PM instance properties container and attributes.";
    container properties {
      ui:ui-name "Instance Properties";
      description
        "PM instance properties.";
      leaf configuration-mode {
        ui:ui-name "Configuration Mode";
        type pm-configuration-mode;
        config false;
        description
          "The PM instance configuration mode";
      }

      leaf tca-profile-15-min {
        ui:ui-name "TCA Profile Name 15-min";
        type cienawstypes:string-maxl-32;
        description
          "TCA profile name that is attached to the current 15 minute bin";
      }

      leaf tca-profile-24-hr {
        ui:ui-name "TCA Profile Name 24-hr";
        type cienawstypes:string-maxl-32;
        description
          "TCA profile name that is attached to the current 24 hour bin";
      }

      leaf tca-profile-untimed {
        ui:ui-name "TCA Profile Name untimed";
        type cienawstypes:string-maxl-32;
        description
          "TCA profile name that is attached to the untimed bin";
      }

      leaf configured-bin-count {
        ui:ui-name "Configured Bin Count";
        type uint32;
        config false;
        description
          "The configured number of history bins.";
      }

      leaf configured-bin-duration {
        ui:ui-name "Configured Bin Duration";
        type uint32;
        units "minutes";
        config false;
        description
          "The configured PM bin duration in minutes.";
      }
    }

    container attached-interface {
      ui:ui-name "Attached Interface";
      config false;
      description
        "Attached interface.";
      leaf type {
        ui:ui-name "Interface Type";
        type pm-interface-type;
        description
          "Attached interface type.";
      }

      leaf name {
        ui:ui-name "Interface Name";
        type cienawstypes:string-maxl-32;
        description
          "Attached interface name.";
      }

      leaf operational-state {
        ui:ui-name "Operational State";
        type cienawstypes:enabled-disabled-enum;
        description
          "Attached interface operational state.";
      }
    }
  }

  grouping pm-bin-id-container {
    description
      "Grouping for PM bin id container and attributes.";
    container id {
      ui:ui-name "Bin Id";
      config false;
      description
        "PM Bin identification.";
      leaf bin-name {
        ui:ui-name "Bin Name";
        type cienawstypes:string-maxl-32;
        description
          "The PM bin name.";
      }
    }
  }

  grouping pm-current-bin-state-container {
    description
      "Grouping for PM current bin state container and attributes.";
    container state {
      ui:ui-name "Bin State";
      config false;
      description
        "PM bin state.";
      leaf start-date-time {
        ui:ui-name "Start Date And Time";
        type cienawstypes:string-maxl-32;
        description
          "The PM bin start date and time, in 'YYYY-MM-DDTHH:MM:SS[+|-]hh:mm'
           format, or omitted if not applicable or unavailable.

           The string format follows IETF yang date-and-time specifications, compliant
           with RFC-6991. The base date and time portion of the string represents
           Coordinated Universal Time (UTC), and a non-zero hh:mm offset suffix indicates the
           system-configured local timezone offset at the time the event was recorded, and not
           necessarily when it was retrieved.

           When system timezone is set to UTC or no time-offset value is provisioned,
           the '+00:00' suffix will be used to indicate UTC time with no local offset.";
        reference
          "RFC 3339: Date and Time on the Internet: Timestamps
           RFC 6991: Common Yang Data Types";
      }

      leaf cleared-date-time {
        ui:ui-name "Cleared Date And Time";
        type cienawstypes:string-maxl-32;
        description
          "The PM bin cleared date and time, in 'YYYY-MM-DDTHH:MM:SS[+|-]hh:mm'
           format, or omitted if not applicable or unavailable.

           The string format follows IETF yang date-and-time specifications, compliant
           with RFC-6991. The base date and time portion of the string represents
           Coordinated Universal Time (UTC), and a non-zero hh:mm offset suffix indicates the
           system-configured local timezone offset at the time the event was recorded, and not
           necessarily when it was retrieved.

           When system timezone is set to UTC or no time-offset value is provisioned,
           the '+00:00' suffix will be used to indicate UTC time with no local offset.";
        reference
          "RFC 3339: Date and Time on the Internet: Timestamps
           RFC 6991: Common Yang Data Types";
      }
    }
  }

  grouping pm-history-bin-state-container {
    description
      "Grouping for PM history bin state container and attributes.";
    container state {
      ui:ui-name "Bin State";
      config false;
      description
        "PM bin state.";
      leaf start-date-time {
        ui:ui-name "Start Date And Time";
        type cienawstypes:string-maxl-32;
        description
          "The PM bin starting date and time, in 'YYYY-MM-DDTHH:MM:SS[+|-]hh:mm'
           format, or omitted if not applicable or unavailable.

           The string format follows IETF yang date-and-time specifications, compliant
           with RFC-6991. The base date and time portion of the string represents
           Coordinated Universal Time (UTC), and a non-zero hh:mm offset suffix indicates the
           system-configured local timezone offset at the time the event was recorded, and not
           necessarily when it was retrieved.

           When system timezone is set to UTC or no time-offset value is provisioned,
           the '+00:00' suffix will be used to indicate UTC time with no local offset.";
        reference
          "RFC 3339: Date and Time on the Internet: Timestamps
           RFC 6991: Common Yang Data Types";
      }

      leaf end-date-time {
        ui:ui-name "End Date And Time";
        type cienawstypes:string-maxl-32;
        description
          "The PM bin end date and time, in 'YYYY-MM-DDTHH:MM:SS[+|-]hh:mm'
           format, or omitted if not applicable or unavailable.

           The string format follows IETF yang date-and-time specifications, compliant
           with RFC-6991. The base date and time portion of the string represents
           Coordinated Universal Time (UTC), and a non-zero hh:mm offset suffix indicates the
           system-configured local timezone offset at the time the event was recorded, and not
           necessarily when it was retrieved.

           When system timezone is set to UTC or no time-offset value is provisioned,
           the '+00:00' suffix will be used to indicate UTC time with no local offset.";
        reference
          "RFC 3339: Date and Time on the Internet: Timestamps
           RFC 6991: Common Yang Data Types";
      }
    }
  }

  grouping pm-counter-meta {
    description
      "Grouping for PM counter metadata, including IDF and supported flags.";
    leaf invalid-data-flag {
      ui:ui-name "IDF";
      type boolean;
      description
        "Invalid Data Flag (IDF) value. Reports the validity of the corresponding
         PM data. Reported only with previous interval PM counters. A value of true
         indicates the PM data for the specified counter or interval is incomplete
         or invalid.";
      reference
        "ITU-T G.997.2, sections 7.7.2 and 7.8.2.";
    }

    leaf supported {
      ui:ui-name "Supported";
      type boolean;
      description
        "Indicates whether the specified counter is supported on associated
         hardware version and interface type.";
    }

    leaf tca-supported {
      ui:ui-name "TCA Supported";
      type boolean;
      description
        "Indicates whether the specified counter supports TCA.";
    }

    leaf tca-active {
      ui:ui-name "TCA Active";
      type boolean;
      description
        "Indicates whether the specified counter has TCA raised against it.";
    }
  }

  grouping pm-counter32-signed-group {
    description
      "Grouping for signed PM counters, including count value and metadata.";
    leaf value {
      type int32;
      description
        "PM counter value, for signed 32-bit integer counter values.";
    }

    leaf tca-threshold {
      type int32;
      description
        "PM counter TCA threshold.";
    }

    uses pm-counter-meta;
  }

  grouping pm-counter-group {
    description
      "Grouping for basic PM counters, including count value and metadata.";
    leaf value {
      ui:ui-name "Value";
      type uint64;
      description
        "PM counter value.";
    }

    leaf tca-threshold {
      ui:ui-name "TCA Threshold";
      type uint64;
      description
        "PM counter TCA threshold.";
    }

    uses pm-counter-meta;
  }

  grouping pm-counter-signed-group {
    description
      "Grouping for signed PM counters, including count value and metadata.";
    leaf value {
      ui:ui-name "Value";
      type int64;
      description
        "PM counter value, for signed integer counter values.";
    }

    leaf tca-threshold {
      ui:ui-name "TCA Threshold";
      type int64;
      description
        "PM counter TCA threshold, for signed integer counter values.";
    }

    uses pm-counter-meta;
  }

  grouping pm-counter-percent-group {
    description
      "Grouping for PM counters with percent units, including count value and metadata.";
    leaf value {
      ui:ui-name "Value";
      type cienawstypes:decimal-3-dig;
      units "percent";
      description
        "PM value, as a percentage.";
    }

    leaf tca-threshold {
      ui:ui-name "TCA Threshold";
      type cienawstypes:decimal-3-dig;
      units "percent";
      description
        "PM TCA threshold value, as a percentage.";
    }

    uses pm-counter-meta;
  }

  grouping pm-counter-dbm-group {
    description
      "Grouping for PM counters with dBm units, including count value and metadata.";
    leaf value {
      ui:ui-name "Value";
      type cienawstypes:decimal-3-dig;
      units "dBm";
      description
        "PM value, as a power level in dBm.";
    }

    leaf tca-threshold {
      ui:ui-name "TCA Threshold";
      type cienawstypes:decimal-3-dig;
      units "dBm";
      description
        "PM TCA threshold value, as a power level in dBm.";
    }

    uses pm-counter-meta;
  }

  grouping pm-counter-db-group {
    description
      "Grouping for PM counters with dB units, including count value and metadata.";
    leaf value {
      ui:ui-name "Value";
      type cienawstypes:decimal-3-dig;
      units "dB";
      description
        "PM value, as loss or gain in dB.";
    }

    leaf tca-threshold {
      ui:ui-name "TCA Threshold";
      type cienawstypes:decimal-3-dig;
      units "dB";
      description
        "PM TCA threshold value, as loss or gain in dB.";
    }

    uses pm-counter-meta;
  }

  grouping pm-counter-ps-nm-group {
    description
      "Grouping for PM counters with picosecond per nanometer (ps/nm) units,
       including count value and metadata.";
    leaf value {
      ui:ui-name "Value";
      type cienawstypes:decimal-3-dig;
      units "ps/nm";
      description
        "PM value, in picoseconds per nanometer (ps/nm).";
    }

    leaf tca-threshold {
      ui:ui-name "TCA Threshold";
      type cienawstypes:decimal-3-dig;
      units "ps/nm";
      description
        "PM TCA threshold value, in picoseconds per nanometer (ps/nm).";
    }

    uses pm-counter-meta;
  }

  grouping pm-counter-qfac-group {
    description
      "Grouping for q-factor PMs, including count value and metadata.";
    leaf value {
      ui:ui-name "Value";
      type cienawstypes:decimal-3-dig;
      description
        "PM value, as a q-factor.";
    }

    leaf tca-threshold {
      ui:ui-name "TCA Threshold";
      type cienawstypes:decimal-3-dig;
      description
        "PM TCA threshold value, as a q-factor.";
    }

    uses pm-counter-meta;
  }

  grouping pm-counter-ber-group {
    description
      "Grouping for BER PM counters in scientific notation, including count value and metadata.";
    leaf value {
      ui:ui-name "Value";
      type cienawstypes:string-sci;
      description
        "PM value, as a bit error rate in scientific notation.";
    }

    leaf tca-threshold {
      ui:ui-name "TCA Threshold";
      type cienawstypes:string-sci;
      description
        "PM TCA threshold value, as a bit error rate in scientific notation.";
    }

    uses pm-counter-meta;
  }

  grouping pm-counter-krads-group {
    description
      "Grouping for PM counters with kiloradian per second (krad/s) units, including count value and metadata.";
    leaf value {
      ui:ui-name "Value";
      type cienawstypes:decimal-1-dig;
      units "krads/s";
      description
        "PM value, as a kiloradian per second (krad/s).";
    }

    leaf tca-threshold {
      ui:ui-name "TCA Threshold";
      type cienawstypes:decimal-1-dig;
      units "krads/s";
      description
        "PM TCA threshold value, as a kiloradian per second (krad/s).";
    }

    uses pm-counter-meta;
  }

  grouping pm-counter-ps2-group {
    description
      "Grouping for PM counters with picosecond square (ps^2) units with 3 decimal precision,
       including count value and metadata.";
    leaf value {
      ui:ui-name "Value";
      type cienawstypes:decimal-3-dig;
      units "ps^2";
      description
        "PM value, in picoseconds square (ps^2).";
    }

    leaf tca-threshold {
      ui:ui-name "TCA Threshold";
      type cienawstypes:decimal-3-dig;
      units "ps^2";
      description
        "PM TCA threshold value, in picoseconds square (ps^2).";
    }

    uses pm-counter-meta;
  }

  grouping ethernet-pm-counts-rx {
    description
      "Grouping for Ethernet port PM Rx counters.";
    container bytes {
      ui:ui-name "Rx bytes";
      description
        "Number of bytes received including good and bad packets. This includes
         FCS bytes, but excludes framing bits.";
      uses pm-counter-group;
    }

    container packets {
      ui:ui-name "Rx packets";
      description
        "Number of packets received, including all unicast, multicast, broadcast,
         MAC control, and bad packets";
      uses pm-counter-group;
    }

    container crc-errored-packets {
      ui:ui-name "Rx CRC errored packets";
      description
        "Number of packets received which contained an FCS error and were
         between 64 and 1518 bytes in length.";
      uses pm-counter-group;
    }

    container multicast-packets {
      ui:ui-name "Rx multicast packets";
      description
        "Number of good multicast packets received that were between 64 and
         1518 bytes in length. Excludes MAC control frames";
      uses pm-counter-group;
    }

    container broadcast-packets {
      ui:ui-name "Rx broadcast packets";
      description
        "Number of good broadcast packets received that were between 64 and
         1518 bytes in length. Excludes MAC control frames";
      uses pm-counter-group;
    }

    container undersized-packets {
      ui:ui-name "Undersized packets";
      description
        "Number of packets received that were less than 64 bytes (excluding
         framing bits but including FCS bytes) and were otherwise well formed.
         This counter also includes the number of packets discarded because of
         Ethernet length check errors. Undersize packets are discarded.";
      uses pm-counter-group;
    }

    container oversized-packets {
      ui:ui-name "Oversized packets";
      description
        "Number of packets received (including unicast, multicast, and broadcast
         packets) that were longer than 1518 bytes up to the configured maximum
         frame size, that contained a valid FCS (excluding framing bits but
         including FCS bytes), and that were otherwise well formed";
      uses pm-counter-group;
    }

    container fragment-packets {
      ui:ui-name "Fragment packets";
      description
        "Number of packets received between 10 and 63 bytes in length (excluding
         framing bits but including FCS bytes) that had either a bad FCS with an
         integral number of bytes (FCS Error) or a bad FCS with a non-integral
         number of bytes (Alignment Error). Fragment packets are discarded.";
      uses pm-counter-group;
    }

    container jabber-packets {
      ui:ui-name "Jabber packets";
      description
        "Number of packets received that were longer than 1518 bytes up to the
         configured maximum frame size (excluding framing bits, but including
         FCS bytes), and had either a bad FCS with an integral number of
         bytes (FCS Error) or a bad FCS with a non-integral number of
         bytes (Alignment Error). Jabber packets are discarded";
      uses pm-counter-group;
    }

    container length-out-of-range-packets {
      ui:ui-name "Rx length out of range packets";
      description
        "Number of Rx length out-of-range packets transmitted";
      uses pm-counter-group;
    }

    container pause-packets {
      ui:ui-name "Rx pause packets";
      description
        "Number of received valid pause packets that were between 64 and 1518 bytes in length";
      uses pm-counter-group;
    }

    container packets-64-octet {
      ui:ui-name "64 octet packets";
      description
        "Number of packets (including bad packets) received that were 64 bytes in
         length (excluding framing bits but including FCS bytes).";
      uses pm-counter-group;
    }

    container packets-65-127-octet {
      ui:ui-name "65 to 127 octet packets";
      description
        "Number of good and bad packets received that were between 65 and 127 bytes in
         length (excluding framing bits but including FCS bytes).";
      uses pm-counter-group;
    }

    container packets-128-255-octet {
      ui:ui-name "128 to 255 octet packets";
      description
        "Number of good and bad packets received that were between 128 and 255 bytes in
         length inclusive (excluding framing bits but including FCS bytes).";
      uses pm-counter-group;
    }

    container packets-256-511-octet {
      ui:ui-name "256 to 511 octet packets";
      description
        "Number of good and bad packets received that were between 256 and 511 bytes in
         length inclusive (excluding framing bits but including FCS bytes).";
      uses pm-counter-group;
    }

    container packets-512-1023-octet {
      ui:ui-name "512 to 1023 octet packets";
      description
        "Number of good and bad packets received that were between 512 and 1023 bytes in
         length inclusive (excluding framing bits but including FCS bytes).";
      uses pm-counter-group;
    }

    container packets-1024-1518-octet {
      ui:ui-name "1024 to 1518 octet packets";
      description
        "Number of good and bad packets received that were between 1024 and 1518 bytes in
         length inclusive (excluding framing bits but including FCS bytes).";
      uses pm-counter-group;
    }

    container packets-1519-jumbo-octet {
      ui:ui-name "1519 to jumbo octet packets";
      description
        "Number of good and bad packets received that were between 1519 bytes in
         length up to MTU size (excluding framing bits but including FCS bytes).";
      uses pm-counter-group;
    }

    container jumbo-octet-packets {
      ui:ui-name "Jumbo octet packets";
      description
        "Number of good and bad packets received that were greater than MTU size.";
      uses pm-counter-group;
    }

    container bytes-per-second {
      ui:ui-name "Bytes per second";
      description
        "Average number bytes received per second during this period.";
      uses pm-counter-group;
    }

    container frames-per-second {
      ui:ui-name "Frames per second";
      description
        "Average number frames received per second during this period.";
      uses pm-counter-group;
    }

    container average-link-utilization {
      ui:ui-name "Average Link Utilization";
      description
        "Average percent utilization derived from Rx bytes and port speed.";
      uses pm-counter-percent-group;
    }

    container minimum-link-utilization {
      ui:ui-name "Minimum Link Utilization";
      description
        "Minimum percent utilization derived from Rx bytes and port speed.";
      uses pm-counter-percent-group;
    }

    container maximum-link-utilization {
      ui:ui-name "Maximum Link Utilization";
      description
        "Maximum percent utilization derived from Rx bytes and port speed.";
      uses pm-counter-percent-group;
    }

    container block-errors {
      ui:ui-name "Block Errors";
      description
        "PCS block errors.";
      uses pm-counter-group;
    }

    container multilane-bip-errors {
      ui:ui-name "Multilane BIP Errors";
      description
        "PCS lane BIP errors.";
      uses pm-counter-group;
    }

    container frame-error-ratio {
      ui:ui-name "Frame Error Ratio";
      description
        "Frame error ratio, expressed in exponential notation.";
      uses pm-counter-ber-group;
    }
  }

  grouping ethernet-pm-counts-tx {
    description
      "Grouping for Ethernet port PM Tx counters.";
    container bytes {
      ui:ui-name "Tx bytes";
      description
        "Number of transmitted bytes in good and bad packets including FCS bytes and
         excluding frame bits.";
      uses pm-counter-group;
    }

    container packets {
      ui:ui-name "Tx packets";
      description
        "Number of transmitted packets, including all unicast, multicast, broadcast,
         MAC control, and bad packets";
      uses pm-counter-group;
    }

    container excessive-deferred-packets {
      ui:ui-name "Tx excessive deferred packets";
      description
        "Number of transmitted packets experiencing two or more deferrals.
         Applicable to copper ports only";
      uses pm-counter-group;
    }

    container underrun-packets {
      ui:ui-name "Tx underrun packets";
      description
        "Number of underrun packets transmitted";
      uses pm-counter-group;
    }

    container crc-errored-packets {
      ui:ui-name "Tx CRC errored packets";
      description
        "Number of transmitted packets with an FCS error";
      uses pm-counter-group;
    }

    container length-check-error-packets {
      ui:ui-name "Tx length check error packets";
      description
        "Number of length check packets transmitted";
      uses pm-counter-group;
    }

    container length-out-of-range-packets {
      ui:ui-name "Tx length out-of-range packets";
      description
        "Number of Tx length out-of-range packets transmitted";
      uses pm-counter-group;
    }

    container pause-packets {
      ui:ui-name "Tx pause packets";
      description
        "Number of pause packets transmitted";
      uses pm-counter-group;
    }

    container giant-packets {
      ui:ui-name "Tx giant packets";
      description
        "Number of well-formed packets larger than 1518 bytes, including FCS bytes
         but excluding framing bits.";
      uses pm-counter-group;
    }

    container multicast-packets {
      ui:ui-name "Tx multicast packets";
      description
        "Number of good multicast packets transmitted";
      uses pm-counter-group;
    }

    container broadcast-packets {
      ui:ui-name "Tx broadcast packets";
      description
        "Number of good broadcast packets transmitted";
      uses pm-counter-group;
    }

    container packets-64-octet {
      ui:ui-name "64 octet packets";
      description
        "Number of packets (including bad packets) transmitted that were 64 bytes in
         length (excluding framing bits but including FCS bytes).";
      uses pm-counter-group;
    }

    container packets-65-127-octet {
      ui:ui-name "65 to 127 octet packets";
      description
        "Number of good and bad packets transmitted that were between 65 and
         127 bytes in length (excluding framing bits but including FCS bytes).";
      uses pm-counter-group;
    }

    container packets-128-255-octet {
      ui:ui-name "128 to 255 octet packets";
      description
        "Number of good and bad packets transmitted that were between 128 and
         255 bytes in length inclusive (excluding framing bits but including FCS bytes).";
      uses pm-counter-group;
    }

    container packets-256-511-octet {
      ui:ui-name "256 to 511 octet packets";
      description
        "Number of good and bad packets transmitted that were between 256 and
         511 bytes in length inclusive (excluding framing bits but including FCS bytes).";
      uses pm-counter-group;
    }

    container packets-512-1023-octet {
      ui:ui-name "512 to 1023 octet packets";
      description
        "Number of good and bad packets transmitted that were between 512 and
         1023 bytes in length inclusive (excluding framing bits but including FCS bytes).";
      uses pm-counter-group;
    }

    container packets-1024-1518-octet {
      ui:ui-name "1024 to 1518 octet packets";
      description
        "Number of good and bad packets transmitted that were between 1024 and
         1518 bytes in length inclusive (excluding framing bits but including FCS bytes).";
      uses pm-counter-group;
    }

    container packets-1519-jumbo-octet {
      ui:ui-name "1519 to jumbo octet packets";
      description
        "Number of good and bad packets transmitted that were between 1519 bytes in
         length up to MTU size (excluding framing bits but including FCS bytes).";
      uses pm-counter-group;
    }

    container jumbo-octet-packets {
      ui:ui-name "Jumbo octet packets";
      description
        "Number of good and bad packets transmitted that were greater than MTU size.";
      uses pm-counter-group;
    }

    container bytes-per-second {
      ui:ui-name "Bytes per second";
      description
        "Average number bytes transmitted per second during this period.";
      uses pm-counter-group;
    }

    container frames-per-second {
      ui:ui-name "Frames per second";
      description
        "Average number frames transmitted per second during this period.";
      uses pm-counter-group;
    }

    container average-link-utilization {
      ui:ui-name "Average Link Utilization";
      description
        "Average percent utilization derived from Tx bytes and port speed.";
      uses pm-counter-percent-group;
    }

    container minimum-link-utilization {
      ui:ui-name "Minimum Link Utilization";
      description
        "Minimum percent utilization derived from Tx bytes and port speed.";
      uses pm-counter-percent-group;
    }

    container maximum-link-utilization {
      ui:ui-name "Maximum Link Utilization";
      description
        "Maximum percent utilization derived from Tx bytes and port speed.";
      uses pm-counter-percent-group;
    }

    container block-errors {
      ui:ui-name "Block Errors";
      description
        "PCS block errors.";
      uses pm-counter-group;
    }

    container multilane-bip-errors {
      ui:ui-name "Multilane BIP Errors";
      description
        "PCS lane BIP errors.";
      uses pm-counter-group;
    }

    container frame-error-ratio {
      ui:ui-name "Frame Error Ratio";
      description
        "Frame error ratio, expressed in exponential notation.";
      uses pm-counter-ber-group;
    }
  }

  grouping gcm-far-end-error-counts {
    description
      "Grouping for common GCM far-end PM error counts (ES, SES).";
    container errored-seconds {
      ui:ui-name "Errored Seconds";
      description
        "Number of seconds that error happened.";
      uses pm-counter-group;
    }

    container severely-errored-seconds {
      ui:ui-name "Severely Errored Seconds";
      description
        "Number of seconds that severe error happened.";
      uses pm-counter-group;
    }
  }

  grouping error-counts {
    description
      "Grouping for common PM error counts (ES, SES, UAS).";
    uses gcm-far-end-error-counts;

    container unavailable-seconds {
      ui:ui-name "Unavailable Seconds";
      description
        "Number of seconds that the interface was unavailable.";
      uses pm-counter-group;
    }
  }

  grouping fec-layer-counts {
    description
      "Grouping for Ethernet port FEC layer counts.";
    container corrected-codeword-count {
      ui:ui-name "Corrected Codeword Count";
      description
        "FEC layer corrected codeword count";
      uses pm-counter-group;
    }

    container uncorrected-codeword-count {
      ui:ui-name "Uncorrected Codeword Count";
      description
        "FEC layer uncorrected codeword count";
      uses pm-counter-group;
    }

    container symbol-error-count {
      ui:ui-name "Symbol Error Count";
      description
        "FEC layer symbol error count. This is the total of error counts across
         all PMA lanes on this interface.";
      uses pm-counter-group;
    }

    container symbol-error-count-lane0 {
      ui:ui-name "Symbol Error Count - Lane 0";
      description
        "FEC layer symbol error count for lane 0.";
      uses pm-counter-group;
    }

    container symbol-error-count-lane1 {
      ui:ui-name "Symbol Error Count - Lane 1";
      description
        "FEC layer symbol error count for lane 1.";
      uses pm-counter-group;
    }

    container symbol-error-count-lane2 {
      ui:ui-name "Symbol Error Count - Lane 2";
      description
        "FEC layer symbol error count for lane 2.";
      uses pm-counter-group;
    }

    container symbol-error-count-lane3 {
      ui:ui-name "Symbol Error Count - Lane 3";
      description
        "FEC layer symbol error count for lane 3.";
      uses pm-counter-group;
    }
  }

  grouping dgd-counts {
    description
      "Differential Group Delay (DGD) Grouping.";
    container maximum {
      ui:ui-name "Maximum DGD";
      description
        "Maximum differential group delay (in ps).";
      uses pm-counter-ps-nm-group;
    }

    container average {
      ui:ui-name "Average DGD";
      description
        "Average differential group delay (in ps).";
      uses pm-counter-ps-nm-group;
    }
  }

  grouping pdl-counts {
    description
      "Polarization Dependent Loss (PDL) Grouping.";
    container maximum {
      ui:ui-name "Maximum PDL";
      description
        "Maximum polarization dependent loss (in dB).";
      uses pm-counter-db-group;
    }

    container average {
      ui:ui-name "Average PDL";
      description
        "Average polarization dependent loss (in dB).";
      uses pm-counter-db-group;
    }
  }

  grouping snr-counts {
    description
      "Signal-to-Noise Ratio (SNR) Grouping, for SNR TNLE, SNR ASE, SNR External and OSNR PM stats.";
    container minimum {
      ui:ui-name "Minimum SNR";
      description
        "Minimum signal-to-noise ratio (in dB).";
      uses pm-counter-db-group;
    }

    container maximum {
      ui:ui-name "Maximum SNR";
      description
        "Maximum signal-to-noise ratio (in dB).";
      uses pm-counter-db-group;
    }

    container average {
      ui:ui-name "Average SNR";
      description
        "Average signal-to-noise ratio (in dB).";
      uses pm-counter-db-group;
    }
  }

  grouping esnr-counts {
    description
      "Signal-to-Noise Ratio (SNR) Grouping for ESNR PM stats.";
    container minimum {
      description
        "Minimum signal-to-noise ratio (in dB).";
      uses pm-counter-db-group;
    }

    container maximum {
      description
        "Maximum signal-to-noise ratio (in dB).";
      uses pm-counter-db-group;
    }

    container average {
      description
        "Average signal-to-noise ratio (in dB).";
      uses pm-counter-db-group;
    }

    container delta {
      description
        "Delta signal-to-noise ratio (in dB).";
      uses pm-counter-db-group;
    }
  }

  grouping csi-counts {
    description
      "Cycle Slip Indicator (CSI) Grouping.";
    container maximum {
      ui:ui-name "Maximum CSI";
      description
        "Maximum cycle slip indicator.";
      uses pm-counter-signed-group;
    }

    container average {
      ui:ui-name "Average CSI";
      description
        "Average cycle slip indicator.";
      uses pm-counter-signed-group;
    }
  }

  grouping cd-counts {
    description
      "Chromatic Dispersion Grouping.";
    container minimum {
      ui:ui-name "Minimum CD";
      description
        "Minimum chromatic dispersion value (in ps/nm).";
      uses pm-counter-signed-group;
    }

    container maximum {
      ui:ui-name "Maximum CD";
      description
        "Maximum chromatic dispersion value (in ps/nm).";
      uses pm-counter-signed-group;
    }

    container average {
      ui:ui-name "Average CD";
      description
        "Average chromatic dispersion value (in ps/nm).";
      uses pm-counter-signed-group;
    }
  }

  grouping cfo-counts {
    description
      "Carrier Frequency Offset Grouping.";
    container minimum {
      description
        "Minimum carrier frequency offset value (in MHz).";
      uses pm-counter32-signed-group;
    }

    container maximum {
      description
        "Maximum carrier frequency offset value (in MHz).";
      uses pm-counter32-signed-group;
    }

    container average {
      description
        "Average carrier frequency offset value (in MHz).";
      uses pm-counter32-signed-group;
    }
  }

  grouping evm-counts {
    description
      "Error Vector Magnitude Grouping.";
    container minimum {
      description
        "Minimum error vector magnitude value.";
      uses pm-counter-percent-group;
    }

    container maximum {
      description
        "Maximum error vector magnitude value.";
      uses pm-counter-percent-group;
    }

    container average {
      description
        "Average error vector magnitude value.";
      uses pm-counter-percent-group;
    }
  }

  grouping power-counts {
    description
      "Optical Power Grouping. Can be used for Tx or Rx optical power PM instances.";
    container minimum {
      ui:ui-name "Minimum Power";
      description
        "Minimum power reading.";
      uses pm-counter-dbm-group;
    }

    container maximum {
      ui:ui-name "Maximum Power";
      description
        "Maximum power reading.";
      uses pm-counter-dbm-group;
    }

    container average {
      ui:ui-name "Average Power";
      description
        "Average power reading.";
      uses pm-counter-dbm-group;
    }

    leaf baseline {
      ui:ui-name "PM TCA Baseline";
      type cienawstypes:decimal-3-dig;
      units "dBm";
      description
        "PM TCA baseline value, as a power level in dBm. Not applicable to history bins.";
    }
  }

  grouping signal-loss-counts {
    description
      "Signal Loss Grouping, for Return Loss and Tx or Rx Span Loss stats.";
    container minimum {
      ui:ui-name "Minimum";
      description
        "Minimum loss (in dB).";
      uses pm-counter-db-group;
    }

    container maximum {
      ui:ui-name "Maximum";
      description
        "Maximum loss (in dB).";
      uses pm-counter-db-group;
    }

    container average {
      ui:ui-name "Average";
      description
        "Average loss (in dB).";
      uses pm-counter-db-group;
    }

    leaf baseline {
      ui:ui-name "PM TCA Baseline";
      type cienawstypes:decimal-3-dig;
      units "dB";
      description
        "PM TCA baseline value in dB. Not applicable to history bins.";
    }
  }

  grouping pm-otdr-counter-signed-group {
    description
      "OTDR Grouping, for OTDR trace counts for Tx or Rx, short and long.";
    container minimum {
      ui:ui-name "Minimum";
      description
        "Minimum count (int).";
      uses pm-counter-signed-group;
    }

    container maximum {
      ui:ui-name "Maximum";
      description
        "Maximum count (int).";
      uses pm-counter-signed-group;
    }

    container current {
      ui:ui-name "Current";
      description
        "Current count (int).";
      uses pm-counter-signed-group;
    }

    leaf baseline {
      ui:ui-name "PM Baseline";
      type int64;
      description
        "PM baseline value (int). Not applicable to history bins.";
    }
  }

  grouping pm-otdr-counter-db-group {
    description
      "OTDR Grouping, for OTDR trace counts for Tx or Rx, short and long.";
    container minimum {
      ui:ui-name "Minimum";
      description
        "Minimum count (in dB).";
      uses pm-counter-db-group;
    }

    container maximum {
      ui:ui-name "Maximum";
      description
        "Maximum count (in dB).";
      uses pm-counter-db-group;
    }

    container current {
      ui:ui-name "Current";
      description
        "Current count (in dB).";
      uses pm-counter-db-group;
    }

    leaf baseline {
      ui:ui-name "PM TCA Baseline";
      type cienawstypes:decimal-3-dig;
      units "dB";
      description
        "PM TCA baseline value in dB. Not applicable to history bins.";
    }
  }

  grouping otdr-counts {
    description
      "OTDR Counts Grouping, for OTDR trace counts for Tx or Rx, short and long.";
    container event-count {
      ui:ui-name "Event Count";
      description
        "Event count (int).";
      uses pm-otdr-counter-signed-group;
    }

    container event-maximum-loss {
      ui:ui-name "Event Maximum Loss";
      description
        "Event maximum loss (in dB).";
      uses pm-otdr-counter-db-group;
    }

    container event-maximum-loss-distance {
      ui:ui-name "Event Maximum Loss Distance";
      description
        "Event maximum loss distance (in dB).";
      uses pm-otdr-counter-db-group;
    }

    container event-maximum-reflection {
      ui:ui-name "Event Maximum Reflection";
      description
        "Event maximum reflection (in dB).";
      uses pm-otdr-counter-db-group;
    }

    container event-maximum-reflection-distance {
      ui:ui-name "Event Maximum Reflection Distance";
      description
        "Event maximum reflection distance (in dB).";
      uses pm-otdr-counter-db-group;
    }

    container cumulative-loss {
      ui:ui-name "Cumulative Loss";
      description
        "Cumulative loss (in dB).";
      uses pm-otdr-counter-db-group;
    }

    container cumulative-reflection {
      ui:ui-name "Cumulative Reflection";
      description
        "Cumulative reflection (in dB).";
      uses pm-otdr-counter-db-group;
    }
  }

  grouping ber-counts {
    description
      "Grouping for common PM Bit-Error-Rate values.";
    container bit-error-rate {
      ui:ui-name "Bit Error Rate";
      description
        "Bit error rate reading.";
      uses pm-counter-ber-group;
    }

    container maximum {
      ui:ui-name "Maximum BER";
      description
        "Maximum BER reading.";
      uses pm-counter-ber-group;
    }
  }

  grouping q-factor-counts {
    description
      "Grouping for PM modem Q-Factor values.";
    container q-factor {
      ui:ui-name "Q-Factor";
      description
        "Average Q-Factor reading.";
      uses pm-counter-qfac-group;
    }

    container minimum {
      ui:ui-name "Minimum Q-Factor";
      description
        "Minimum Q-Factor reading.";
      uses pm-counter-qfac-group;
    }

    container maximum {
      ui:ui-name "Maximum Q-Factor";
      description
        "Maximum Q-Factor reading.";
      uses pm-counter-qfac-group;
    }

    container standard-deviation {
      ui:ui-name "Q-Factor Std Dev";
      description
        "Q-Factor standard deviation value.";
      uses pm-counter-qfac-group;
    }
  }

  grouping fec-error-counts {
    description
      "Grouping for line PTP FEC counts.";
    container uncorrected-block-count {
      ui:ui-name "FEC Uncorrected Block Count";
      description
        "FEC uncorrected block count.";
      uses pm-counter-group;
    }

    container uncorrected-second {
      ui:ui-name "FEC Uncorrected Second";
      description
        "FEC uncorrected second count.";
      uses pm-counter-group;
    }

    container high-correction-count-seconds {
      ui:ui-name "FEC High Correction Count Seconds";
      description
        "FEC high correction count seconds.";
      uses pm-counter-group;
    }
  }

  grouping pm-ethernet-stats-group {
    description
      "Grouping for Ethernet port statistics containers and attributes.";
    container interface-counts {
      ui:ui-name "Interface Counts";
      description
        "Ethernet PM interface counts.";
      container rx {
        ui:ui-name "RX Counts";
        description
          "Ethernet interface Rx counts.";
        uses ethernet-pm-counts-rx;
      }

      container tx {
        ui:ui-name "TX Counts";
        description
          "Ethernet interface Tx counts.";
        uses ethernet-pm-counts-tx;
      }
    }

    container pcs-layer {
      ui:ui-name "PCS Layer";
      description
        "PCS layer statistics.";
      container sync-header-errors {
        ui:ui-name "Sync Header Errors";
        description
          "PCS sync header errors.";
        uses pm-counter-group;
      }

      uses error-counts;
    }

    container fec-layer {
      ui:ui-name "FEC Layer";
      description
        "Ethernet FEC layer PM statistics.";
      uses fec-layer-counts;
    }
  }

  grouping pm-optical-power-stats-group {
    description
      "Grouping for PTP optical power statistics containers and attributes.";
    leaf number-of-lanes {
      ui:ui-name "Number of Lanes";
      type uint16;
      description
        "Number of optical lanes.";
    }

    list optical-power {
      ui:ui-name "Lanes";
      key "lane-number";
      config false;
      max-elements 8;
      description
        "Statistics for a PTP optical lane.";
      leaf lane-number {
        ui:ui-name "Lane Number";
        type cienawstypes:lanes-number;
        config false;
        description
          "Lane number.";
      }

      container rx-power {
        ui:ui-name "Rx Power";
        config false;
        description
          "Rx power reading.";
        uses power-counts;
      }

      container tx-power {
        ui:ui-name "Tx Power";
        config false;
        description
          "Tx power reading.";
        uses power-counts;
      }
    }

    container channel-power {
      ui:ui-name "Channel Power";
      config false;
      description
        "Total optical channel power readings. Only applies to line PTP in 'colourless' mode.";
      container rx-power {
        ui:ui-name "Rx Power";
        config false;
        description
          "Rx power reading.";
        uses power-counts;
      }
    }

    container aggregate-power {
      ui:ui-name "Aggregate Power";
      config false;
      description
        "For OTM PTP instances, this contains the total DWDM + OSC power readings.";
      container rx-power {
        ui:ui-name "Rx Power";
        config false;
        description
          "Rx aggregate power reading.";
        uses power-counts;
      }

      container tx-power {
        ui:ui-name "Tx Power";
        config false;
        description
          "Tx aggregate power reading.";
        uses power-counts;
      }
    }
  }

  grouping pm-photonics-stats-group {
    description
      "Grouping for OTM PTP photonics statistics.";
    container return-loss {
      ui:ui-name "Return Loss";
      config false;
      description
        "Return Loss measurements.";
      uses signal-loss-counts;
    }

    container rx-span-loss {
      ui:ui-name "Rx Span Loss";
      config false;
      description
        "Rx Span Loss measurements.";
      uses signal-loss-counts;
    }

    container tx-span-loss {
      ui:ui-name "Tx Span Loss";
      config false;
      description
        "Tx Span Loss measurements.";
      uses signal-loss-counts;
    }

    container rx-otdr-trace-short {
      ui:ui-name "Rx OTDR Trace Short";
      config false;
      description
        "Rx OTDR trace counts short.";
      uses otdr-counts;
    }

    container rx-otdr-trace-long {
      ui:ui-name "Rx OTDR Trace Long";
      config false;
      description
        "Rx OTDR trace counts long.";
      uses otdr-counts;
    }

    container tx-otdr-trace-short {
      ui:ui-name "Tx OTDR Trace Short";
      config false;
      description
        "Tx OTDR trace counts short.";
      uses otdr-counts;
    }

    container tx-otdr-trace-long {
      ui:ui-name "Tx OTDR Trace Long";
      config false;
      description
        "Tx OTDR trace counts long.";
      uses otdr-counts;
    }
  }

  grouping pm-modem-stats-group {
    description
      "Grouping for PTP modem statistics containers and attributes.";
    container pre-fec-bit-error-rate {
      ui:ui-name "PRE-FEC BER";
      config false;
      description
        "Pre-FEC BER counts.";
      uses ber-counts;
    }

    container q-factor {
      ui:ui-name "Q-Factor";
      config false;
      description
        "Q-Factor count.";
      uses q-factor-counts;
    }

    container fec-error {
      ui:ui-name "FEC Error";
      config false;
      description
        "FEC error counts.";
      uses fec-error-counts;
    }

    container dgd {
      ui:ui-name "DGD";
      description
        "Differential group delay (DGD) counts.";
      uses dgd-counts;
    }

    container pdl {
      ui:ui-name "PDL";
      description
        "Polarization dependent loss (PDL) counts.";
      uses pdl-counts;
    }

    container esnr {
      ui:ui-name "ESNR";
      description
        "Effective Signal-to-Noise Ratio (ESNR) counts.";
      uses esnr-counts;
    }

    container snre {
      ui:ui-name "SNR External";
      description
        "Signal-to-Noise Ratio (SNR) External counts.";
      uses snr-counts;
    }

    container osnr {
      ui:ui-name "OSNR";
      description
        "Optical Signal-to-Noise Ratio (OSNR) counts.";
      uses snr-counts;
    }

    container snr-ase {
      description
        "Signal-to-Noise Ratio (SNR) Amplified Spontaneous Emission (ASE) counts.";
      uses snr-counts;
    }

    container snr-tnle {
      description
        "Signal-to-Noise Ratio (SNR) Total Non Linear Noise Estimate (TNLE) counts.";
      uses snr-counts;
    }

    container csi {
      ui:ui-name "Cycle Slip Indicator";
      description
        "Cycle Slip Indicator (CSI) counts.";
      uses csi-counts;
    }

    container chromatic-dispersion {
      ui:ui-name "Chromatic Dispersion";
      description
        "Chromatic Dispersion counts.";
      uses cd-counts;
    }

    container carrier-frequency-offset {
      description
        "Carrier Frequency Offset counts.";
      uses cfo-counts;
    }

    container error-vector-magnitude {
      description
        "Error Vector Magnitude counts.";
      uses evm-counts;
    }

    container state-of-polarization-rate-of-change {
      description
        "State of polarization rate of change counts";
      uses state-of-polarization-rate-of-change-counts;
    }

    container modulation-error-ratio {
      description
        "Modulation error ratio counts";
      uses modulation-error-ratio-counts;
    }

    container second-order-polarization-mode-dispersion {
      description
        "Second order polarization mode dispersion counts";
      uses second-order-polarization-mode-dispersion-counts;
    }
  }

  grouping pm-otn-stats-group {
    description
      "Grouping for OTN port/channel statistics containers and attributes.";
    container background-block-errors {
      ui:ui-name "Background Block Errors (BBE)";
      description
        "Background Block Errors (BBE).";
      uses pm-counter-group;
    }

    uses error-counts;

    container far-end {
      description
        "Far-end statistics.";
      container background-block-errors {
        ui:ui-name "Background Block Errors (BBE)";
        description
          "Background Block Errors (BBE).";
        uses pm-counter-group;
      }

      uses error-counts;
    }
  }

  grouping pm-gcm-stats-group {
    description
      "Grouping for Encryption-GCM channel statistics containers and attributes.";
    container error-count {
      ui:ui-name "Error Count";
      status deprecated;
      description
        "GCM tag error count.";
      uses pm-counter-group {
        status deprecated;
      }
    }

    uses error-counts;

    container far-end {
      description
        "Far-end statistics.";
      uses gcm-far-end-error-counts;
    }
  }

  grouping state-of-polarization-rate-of-change-counts {
    description
      "Grouping for state of polarization rate of change values.";
    reference
      "IA OIF-C-CMIS-01.1 Table 7";
    container average {
      ui:ui-name "Average State Of Polarization Rate Of Change";
      description
        "Average state of polarization rate of change reading.";
      uses pm-counter-krads-group;
    }

    container maximum {
      ui:ui-name "Maximum State Of Polarization Rate Of Change";
      description
        "Maximum state of polarization rate of change reading.";
      uses pm-counter-krads-group;
    }

    container minimum {
      ui:ui-name "Minimum State Of Polarization Rate Of Change";
      description
        "Minimum state of polarization rate of change reading.";
      uses pm-counter-krads-group;
    }
  }

  grouping second-order-polarization-mode-dispersion-counts {
    description
      "Grouping for second order polarization mode dispersion values.";
    container average {
      ui:ui-name "Average Second Order Polarization Mode Dispersion";
      description
        "Average second order polarization mode dispersion reading.";
      uses pm-counter-ps2-group;
    }

    container maximum {
      ui:ui-name "Maximum Second Order Polarization Mode Dispersion";
      description
        "Maximum second order polarization mode dispersion reading.";
      uses pm-counter-ps2-group;
    }

    container minimum {
      ui:ui-name "Minimum Second Order Polarization Mode Dispersion";
      description
        "Minimum second order polarization mode dispersion reading.";
      uses pm-counter-ps2-group;
    }
  }

  grouping modulation-error-ratio-counts {
    description
      "Grouping for modulation error ratio values.";
    container average {
      ui:ui-name "Average Modulation Error Ratio";
      description
        "Average modulation error ratio reading.";
      uses pm-counter-db-group;
    }

    container maximum {
      ui:ui-name "Maximum Modulation Error Ratio";
      description
        "Maximum modulation error ratio reading.";
      uses pm-counter-db-group;
    }

    container minimum {
      ui:ui-name "Minimum Modulation Error Ratio";
      description
        "Minimum modulation error ratio reading.";
      uses pm-counter-db-group;
    }
  }

  grouping pm-pg-stats-group {
    description
      "Grouping for protecton group statistics containers and attributes.";
    container switch-count {
      ui:ui-name "Protection switch count";
      description
        "Protection switch count.";
      uses pm-counter-group;
    }
  }

  container waveserver-pm {
    ui:ui-name "Performance Monitoring";
    description
      "Waveserver performance monitoring configuration and operational data.";
    container global-config {
      ui:ui-name "PM Global Configuration";
      description
        "Performance monitoring global configuration on the Waveserver.";
      leaf admin-state {
        ui:ui-name "Global Admin State";
        type cienawstypes:enabled-disabled-enum;
        description
          "Global admin state.";
      }

      leaf untimed-read-and-clear {
        type cienawstypes:enabled-disabled-enum;
        description
          "Global configuration for clearing untimed bin stats on a get request.";
      }

      leaf tca-admin-state {
        ui:ui-name "Global TCA Admin State";
        type cienawstypes:enabled-disabled-enum;
        description
          "Global TCA administrative state.";
      }

      leaf tca-notification-type {
        ui:ui-name "Global TCA Notification Type";
        type tca-notification-type;
        description
          "Global TCA notification type.";
      }
    }

    container auto-created {
      ui:ui-name "PM Auto Created Instances";
      config false;
      description
        "PM auto created instances.";
      list instances {
        ui:ui-name "PM Auto Created Instances";
        key "instance-id";
        config false;
        description
          "PM auto-created instance list.";
        leaf instance-id {
          ui:ui-name "Instance Id";
          type uint32;
          description
            "ID of the PM instance.";
        }

        leaf instance-name {
          ui:ui-name "Instance Name";
          type cienawstypes:string-maxl-32;
          description
            "The PM instance name.";
        }

        leaf admin-state {
          ui:ui-name "Admin State";
          type cienawstypes:enabled-disabled-enum;
          description
            "The configured administrative state of the PM instance.";
        }

        leaf operational-state {
          ui:ui-name "Operational State";
          type cienawstypes:enabled-disabled-enum;
          description
            "The operational state of the PM instance.";
        }

        leaf bin-count {
          ui:ui-name "Bin Count";
          type uint32;
          description
            "The number of history bins.";
        }

        leaf bin-duration {
          ui:ui-name "Bin Duration";
          type uint32;
          units "minutes";
          description
            "The PM bin duration in minutes.";
        }

        leaf attached-interface-type {
          ui:ui-name "Interface Type";
          type pm-interface-type;
          description
            "Attached interface type.";
        }

        leaf attached-interface-name {
          ui:ui-name "Interface Name";
          type cienawstypes:string-maxl-32;
          description
            "Attached interface name.";
        }

        leaf profile-type {
          ui:ui-name "PM Profile Type";
          type pm-profile-type;
          description
            "The PM profile type.";
        }
      }
    }

    list ethernet-performance-instances {
      ui:ui-name "Ethernet Port PM Instance List";
      ncx:user-write "update";
      key "instance-name";
      description
        "Ethernet port PM instances.";
      leaf instance-name {
        ui:ui-name "Instance Name";
        type cienawstypes:string-maxl-32;
        description
          "Unique name for PM instance.";
      }

      uses pm-instance-id-container;

      uses pm-instance-state-container;

      uses pm-instance-properties-container;

      container current-bin {
        ui:ui-name "PM Current 15 Min Bin";
        config false;
        description
          "PM current 15-minute bin.";
        uses pm-bin-id-container;

        uses pm-current-bin-state-container;

        container statistics {
          ui:ui-name "Bin Statistics";
          config false;
          description
            "Statistics data.";
          uses pm-ethernet-stats-group;
        }
      }

      container current-24-hour-bin {
        ui:ui-name "PM Current 24 Hour Bin";
        config false;
        description
          "PM current 24-hour bin.";
        uses pm-bin-id-container;

        uses pm-current-bin-state-container;

        container statistics {
          ui:ui-name "Bin Statistics";
          config false;
          description
            "Statistics data.";
          uses pm-ethernet-stats-group;
        }
      }

      container untimed-bin {
        ui:ui-name "PM Untimed Bin";
        config false;
        description
          "PM untimed bin.";
        uses pm-bin-id-container;

        uses pm-current-bin-state-container;

        container statistics {
          ui:ui-name "Bin Statistics";
          config false;
          description
            "Statistics data.";
          uses pm-ethernet-stats-group;
        }
      }

      container history {
        ui:ui-name "PM History 15 Min";
        config false;
        description
          "PM 15-minute bin history";
        list bins {
          ui:ui-name "PM History 15 Min Bin List";
          key "bin-number";
          config false;
          description
            "PM history 15-minute bin list.";
          leaf bin-number {
            ui:ui-name "Bin Number";
            type uint32 {
              range "1..96";
            }
            description
              "The PM bin number, an index value representing the current position
               in the list of historical PM bins at the time the data is requested.
               1 is the most recent history bin, and 96 is the oldest.";
          }

          uses pm-bin-id-container;

          uses pm-history-bin-state-container;

          container statistics {
            ui:ui-name "Bin Statistics";
            config false;
            description
              "Statistics data.";
            uses pm-ethernet-stats-group;
          }
        }
      }

      container history-24-hour-bin {
        ui:ui-name "PM History 24 Hour Bin";
        config false;
        description
          "PM History 24-hour bin.";
        uses pm-bin-id-container;

        uses pm-history-bin-state-container;

        container statistics {
          ui:ui-name "Bin Statistics";
          config false;
          description
            "Statistics data.";
          uses pm-ethernet-stats-group;
        }
      }
    }

    list optical-power-instances {
      ui:ui-name "PTP Optical Power PM Instance List";
      ncx:user-write "update";
      key "instance-name";
      description
        "PTP Optical Power PM instances.";
      leaf instance-name {
        ui:ui-name "Instance Name";
        type cienawstypes:string-maxl-32;
        description
          "Unique name for PM instance.";
      }

      uses pm-instance-id-container;

      uses pm-instance-state-container;

      uses pm-instance-properties-container;

      container current-bin {
        ui:ui-name "PM Current 15 Min Bin";
        config false;
        description
          "PM current 15-minute bin.";
        uses pm-bin-id-container;

        uses pm-current-bin-state-container;

        container statistics {
          ui:ui-name "Bin Statistics";
          config false;
          description
            "Statistics data.";
          uses pm-optical-power-stats-group;
        }
      }

      container current-24-hour-bin {
        ui:ui-name "PM Current 24 Hour Bin";
        config false;
        description
          "PM current 24-hour bin.";
        uses pm-bin-id-container;

        uses pm-current-bin-state-container;

        container statistics {
          ui:ui-name "Bin Statistics";
          config false;
          description
            "Statistics data.";
          uses pm-optical-power-stats-group;
        }
      }

      container untimed-bin {
        ui:ui-name "PM Untimed Bin";
        config false;
        description
          "PM untimed bin.";
        uses pm-bin-id-container;

        uses pm-current-bin-state-container;

        container statistics {
          ui:ui-name "Bin Statistics";
          config false;
          description
            "Statistics data.";
          uses pm-optical-power-stats-group;
        }
      }

      container history {
        ui:ui-name "PM History 15 Min";
        config false;
        description
          "PM 15-minute bin history.";
        list bins {
          ui:ui-name "PM History 15 Min Bin List";
          key "bin-number";
          config false;
          description
            "PM history 15-minute bin list.";
          leaf bin-number {
            ui:ui-name "Bin Number";
            type uint32 {
              range "1..96";
            }
            description
              "The PM bin number, an index value representing the current position
               in the list of historical PM bins at the time the data is requested.
               1 is the most recent history bin, and 96 is the oldest.";
          }

          uses pm-bin-id-container;

          uses pm-history-bin-state-container;

          container statistics {
            ui:ui-name "Bin Statistics";
            config false;
            description
              "Statistics data.";
            uses pm-optical-power-stats-group;
          }
        }
      }

      container history-24-hour-bin {
        ui:ui-name "PM History 24 Hour Bin";
        config false;
        description
          "PM History 24-hour bin.";
        uses pm-bin-id-container;

        uses pm-history-bin-state-container;

        container statistics {
          ui:ui-name "Bin Statistics";
          config false;
          description
            "Statistics data.";
          uses pm-optical-power-stats-group;
        }
      }
    }

    list photonics-instances {
      ui:ui-name "PTP Photonics PM Instance List";
      ncx:user-write "update";
      key "instance-name";
      description
        "PTP Photonics PM instances.";
      leaf instance-name {
        ui:ui-name "Instance Name";
        type cienawstypes:string-maxl-32;
        description
          "Unique name for PM instance.";
      }

      uses pm-instance-id-container;

      uses pm-instance-state-container;

      uses pm-instance-properties-container;

      container current-bin {
        ui:ui-name "PM Current 15 Min Bin";
        config false;
        description
          "PM current 15-minute bin.";
        uses pm-bin-id-container;

        uses pm-current-bin-state-container;

        container statistics {
          ui:ui-name "Bin Statistics";
          config false;
          description
            "Statistics data.";
          uses pm-photonics-stats-group;
        }
      }

      container current-24-hour-bin {
        ui:ui-name "PM Current 24 Hour Bin";
        config false;
        description
          "PM current 24-hour bin.";
        uses pm-bin-id-container;

        uses pm-current-bin-state-container;

        container statistics {
          ui:ui-name "Bin Statistics";
          config false;
          description
            "Statistics data.";
          uses pm-photonics-stats-group;
        }
      }

      container untimed-bin {
        ui:ui-name "PM Untimed Bin";
        config false;
        description
          "PM untimed bin.";
        uses pm-bin-id-container;

        uses pm-current-bin-state-container;

        container statistics {
          ui:ui-name "Bin Statistics";
          config false;
          description
            "Statistics data.";
          uses pm-photonics-stats-group;
        }
      }

      container history {
        ui:ui-name "PM History 15 Min";
        config false;
        description
          "PM 15-minute bin history.";
        list bins {
          ui:ui-name "PM History 15 Min Bin List";
          key "bin-number";
          config false;
          description
            "PM history 15-minute bin list.";
          leaf bin-number {
            ui:ui-name "Bin Number";
            type uint32 {
              range "1..96";
            }
            description
              "The PM bin number, an index value representing the current position
               in the list of historical PM bins at the time the data is requested.
               1 is the most recent history bin, and 96 is the oldest.";
          }

          uses pm-bin-id-container;

          uses pm-history-bin-state-container;

          container statistics {
            ui:ui-name "Bin Statistics";
            config false;
            description
              "Statistics data.";
            uses pm-photonics-stats-group;
          }
        }
      }

      container history-24-hour-bin {
        ui:ui-name "PM History 24 Hour Bin";
        config false;
        description
          "PM History 24-hour bin.";
        uses pm-bin-id-container;

        uses pm-history-bin-state-container;

        container statistics {
          ui:ui-name "Bin Statistics";
          config false;
          description
            "Statistics data.";
          uses pm-photonics-stats-group;
        }
      }
    }

    list modem-performance-instances {
      ui:ui-name "PTP Modem PM Instance List";
      ncx:user-write "update";
      key "instance-name";
      description
        "PTP Modem PM instances.";
      leaf instance-name {
        ui:ui-name "Instance Name";
        type cienawstypes:string-maxl-32;
        description
          "Unique name for PM instance.";
      }

      uses pm-instance-id-container;

      uses pm-instance-state-container;

      uses pm-instance-properties-container;

      container current-bin {
        ui:ui-name "PM Current 15 Min Bin";
        config false;
        description
          "PM current 15-minute bin.";
        uses pm-bin-id-container;

        uses pm-current-bin-state-container;

        container statistics {
          ui:ui-name "Bin Statistics";
          config false;
          description
            "Statistics data.";
          uses pm-modem-stats-group;
        }
      }

      container current-24-hour-bin {
        ui:ui-name "PM Current 24 Hour Bin";
        config false;
        description
          "PM current 24-hour bin.";
        uses pm-bin-id-container;

        uses pm-current-bin-state-container;

        container statistics {
          ui:ui-name "Bin Statistics";
          config false;
          description
            "Statistics data.";
          uses pm-modem-stats-group;
        }
      }

      container untimed-bin {
        ui:ui-name "PM Untimed Bin";
        config false;
        description
          "PM untimed bin.";
        uses pm-bin-id-container;

        uses pm-current-bin-state-container;

        container statistics {
          ui:ui-name "Bin Statistics";
          config false;
          description
            "Statistics data.";
          uses pm-modem-stats-group;
        }
      }

      container history {
        ui:ui-name "PM History 15 Min";
        config false;
        description
          "PM 15-minute bin history.";
        list bins {
          ui:ui-name "PM History 15 Min Bin List";
          key "bin-number";
          config false;
          description
            "PM history 15-minute bin list.";
          leaf bin-number {
            ui:ui-name "Bin Number";
            type uint32 {
              range "1..96";
            }
            description
              "The PM bin number, an index value representing the current position
               in the list of historical PM bins at the time the data is requested.
               1 is the most recent history bin, and 96 is the oldest.";
          }

          uses pm-bin-id-container;

          uses pm-history-bin-state-container;

          container statistics {
            ui:ui-name "Bin Statistics";
            config false;
            description
              "Statistics data.";
            uses pm-modem-stats-group;
          }
        }
      }

      container history-24-hour-bin {
        ui:ui-name "PM History 24 Hour Bin";
        config false;
        description
          "PM History 24-hour bin.";
        uses pm-bin-id-container;

        uses pm-history-bin-state-container;

        container statistics {
          ui:ui-name "Bin Statistics";
          config false;
          description
            "Statistics data.";
          uses pm-modem-stats-group;
        }
      }
    }

    list otu-performance-instances {
      ui:ui-name "Port OTU PM Instance List";
      ncx:user-write "update";
      key "instance-name";
      description
        "Port OTU PM instances.";
      leaf instance-name {
        ui:ui-name "Instance Name";
        type cienawstypes:string-maxl-32;
        description
          "Unique name for PM instance.";
      }

      uses pm-instance-id-container;

      uses pm-instance-state-container;

      uses pm-instance-properties-container;

      container current-bin {
        ui:ui-name "PM Current 15 Min Bin";
        config false;
        description
          "PM current 15-minute bin.";
        uses pm-bin-id-container;

        uses pm-current-bin-state-container;

        container statistics {
          ui:ui-name "Bin Statistics";
          config false;
          description
            "Statistics data.";
          uses pm-otn-stats-group;
        }
      }

      container current-24-hour-bin {
        ui:ui-name "PM Current 24 Hour Bin";
        config false;
        description
          "PM current 24-hour bin.";
        uses pm-bin-id-container;

        uses pm-current-bin-state-container;

        container statistics {
          ui:ui-name "Bin Statistics";
          config false;
          description
            "Statistics data.";
          uses pm-otn-stats-group;
        }
      }

      container untimed-bin {
        ui:ui-name "PM Untimed Bin";
        config false;
        description
          "PM untimed bin.";
        uses pm-bin-id-container;

        uses pm-current-bin-state-container;

        container statistics {
          ui:ui-name "Bin Statistics";
          config false;
          description
            "Statistics data.";
          uses pm-otn-stats-group;
        }
      }

      container history {
        ui:ui-name "PM History 15 Min";
        config false;
        description
          "PM 15-minute bin history.";
        list bins {
          ui:ui-name "PM History 15 Min Bin List";
          key "bin-number";
          config false;
          description
            "PM history 15-minute bin list.";
          leaf bin-number {
            ui:ui-name "Bin Number";
            type uint32 {
              range "1..96";
            }
            description
              "The PM bin number, an index value representing the current position
               in the list of historical PM bins at the time the data is requested.
               1 is the most recent history bin, and 96 is the oldest.";
          }

          uses pm-bin-id-container;

          uses pm-history-bin-state-container;

          container statistics {
            ui:ui-name "Bin Statistics";
            config false;
            description
              "Statistics data.";
            uses pm-otn-stats-group;
          }
        }
      }

      container history-24-hour-bin {
        ui:ui-name "PM History 24 Hour Bin";
        config false;
        description
          "PM History 24-hour bin.";
        uses pm-bin-id-container;

        uses pm-history-bin-state-container;

        container statistics {
          ui:ui-name "Bin Statistics";
          config false;
          description
            "Statistics data.";
          uses pm-otn-stats-group;
        }
      }
    }

    list odu-performance-instances {
      ui:ui-name "Port/Channel ODU PM Instance List";
      ncx:user-write "update";
      key "instance-name";
      description
        "Port/channel ODU PM instances.";
      leaf instance-name {
        ui:ui-name "Instance Name";
        type cienawstypes:string-maxl-32;
        description
          "Unique name for PM instance.";
      }

      uses pm-instance-id-container;

      uses pm-instance-state-container;

      uses pm-instance-properties-container;

      container current-bin {
        ui:ui-name "PM Current 15 Min Bin";
        config false;
        description
          "PM current 15-minute bin.";
        uses pm-bin-id-container;

        uses pm-current-bin-state-container;

        container statistics {
          ui:ui-name "Bin Statistics";
          config false;
          description
            "Statistics data.";
          uses pm-otn-stats-group;
        }
      }

      container current-24-hour-bin {
        ui:ui-name "PM Current 24 Hour Bin";
        config false;
        description
          "PM current 24-hour bin.";
        uses pm-bin-id-container;

        uses pm-current-bin-state-container;

        container statistics {
          ui:ui-name "Bin Statistics";
          config false;
          description
            "Statistics data.";
          uses pm-otn-stats-group;
        }
      }

      container untimed-bin {
        ui:ui-name "PM Untimed Bin";
        config false;
        description
          "PM untimed bin.";
        uses pm-bin-id-container;

        uses pm-current-bin-state-container;

        container statistics {
          ui:ui-name "Bin Statistics";
          config false;
          description
            "Statistics data.";
          uses pm-otn-stats-group;
        }
      }

      container history {
        ui:ui-name "PM History 15 Min";
        config false;
        description
          "PM 15-minute bin history.";
        list bins {
          ui:ui-name "PM History 15 Min Bin List";
          key "bin-number";
          config false;
          description
            "PM history 15-minute bin list.";
          leaf bin-number {
            ui:ui-name "Bin Number";
            type uint32 {
              range "1..96";
            }
            description
              "The PM bin number, an index value representing the current position
               in the list of historical PM bins at the time the data is requested.
               1 is the most recent history bin, and 96 is the oldest.";
          }

          uses pm-bin-id-container;

          uses pm-history-bin-state-container;

          container statistics {
            ui:ui-name "Bin Statistics";
            config false;
            description
              "Statistics data.";
            uses pm-otn-stats-group;
          }
        }
      }

      container history-24-hour-bin {
        ui:ui-name "PM History 24 Hour Bin";
        config false;
        description
          "PM History 24-hour bin.";
        uses pm-bin-id-container;

        uses pm-history-bin-state-container;

        container statistics {
          ui:ui-name "Bin Statistics";
          config false;
          description
            "Statistics data.";
          uses pm-otn-stats-group;
        }
      }
    }

    list encryption-gcm-performance-instances {
      ui:ui-name "Channel Encryption GCM PM Instance List";
      ncx:user-write "update";
      key "instance-name";
      description
        "Channel Encryption-GCM PM instances.";
      leaf instance-name {
        ui:ui-name "Instance Name";
        type cienawstypes:string-maxl-32;
        description
          "Unique name for PM instance.";
      }

      uses pm-instance-id-container;

      uses pm-instance-state-container;

      uses pm-instance-properties-container;

      container current-bin {
        ui:ui-name "PM Current 15 Min Bin";
        config false;
        description
          "PM current 15-minute bin.";
        uses pm-bin-id-container;

        uses pm-current-bin-state-container;

        container statistics {
          ui:ui-name "Bin Statistics";
          config false;
          description
            "Statistics data.";
          uses pm-gcm-stats-group;
        }
      }

      container current-24-hour-bin {
        ui:ui-name "PM Current 24 Hour Bin";
        config false;
        description
          "PM current 24-hour bin.";
        uses pm-bin-id-container;

        uses pm-current-bin-state-container;

        container statistics {
          ui:ui-name "Bin Statistics";
          config false;
          description
            "Statistics data.";
          uses pm-gcm-stats-group;
        }
      }

      container untimed-bin {
        ui:ui-name "PM Untimed Bin";
        config false;
        description
          "PM untimed bin.";
        uses pm-bin-id-container;

        uses pm-current-bin-state-container;

        container statistics {
          ui:ui-name "Bin Statistics";
          config false;
          description
            "Statistics data.";
          uses pm-gcm-stats-group;
        }
      }

      container history {
        ui:ui-name "PM History 15 Min";
        config false;
        description
          "PM 15-minute bin history.";
        list bins {
          ui:ui-name "PM History 15 Min Bin List";
          key "bin-number";
          config false;
          description
            "PM history 15-minute bin list.";
          leaf bin-number {
            ui:ui-name "Bin Number";
            type uint32 {
              range "1..96";
            }
            description
              "The PM bin number, an index value representing the current position
               in the list of historical PM bins at the time the data is requested.
               1 is the most recent history bin, and 96 is the oldest.";
          }

          uses pm-bin-id-container;

          uses pm-history-bin-state-container;

          container statistics {
            ui:ui-name "Bin Statistics";
            config false;
            description
              "Statistics data.";
            uses pm-gcm-stats-group;
          }
        }
      }

      container history-24-hour-bin {
        ui:ui-name "PM History 24 Hour Bin";
        config false;
        description
          "PM History 24-hour bin.";
        uses pm-bin-id-container;

        uses pm-history-bin-state-container;

        container statistics {
          ui:ui-name "Bin Statistics";
          config false;
          description
            "Statistics data.";
          uses pm-gcm-stats-group;
        }
      }
    }

    list protection-group-performance-instances {
      ui:ui-name "Protection PM Instance List";
      ncx:user-write "update";
      key "instance-name";
      description
        "Protection PM instances.";
      leaf instance-name {
        ui:ui-name "Instance Name";
        type cienawstypes:string-maxl-32;
        description
          "Unique name for PM instance.";
      }

      uses pm-instance-id-container;

      uses pm-instance-state-container;

      uses pm-instance-properties-container;

      container current-bin {
        ui:ui-name "PM Current 15 Min Bin";
        config false;
        description
          "PM current 15-minute bin.";
        uses pm-bin-id-container;

        uses pm-current-bin-state-container;

        container statistics {
          ui:ui-name "Bin Statistics";
          config false;
          description
            "Statistics data.";
          uses pm-pg-stats-group;
        }
      }

      container current-24-hour-bin {
        ui:ui-name "PM Current 24 Hour Bin";
        config false;
        description
          "PM current 24-hour bin.";
        uses pm-bin-id-container;

        uses pm-current-bin-state-container;

        container statistics {
          ui:ui-name "Bin Statistics";
          config false;
          description
            "Statistics data.";
          uses pm-pg-stats-group;
        }
      }

      container untimed-bin {
        ui:ui-name "PM Untimed Bin";
        config false;
        description
          "PM untimed bin.";
        uses pm-bin-id-container;

        uses pm-current-bin-state-container;

        container statistics {
          ui:ui-name "Bin Statistics";
          config false;
          description
            "Statistics data.";
          uses pm-pg-stats-group;
        }
      }

      container history {
        ui:ui-name "PM History 15 Min";
        config false;
        description
          "PM 15-minute bin history.";
        list bins {
          ui:ui-name "PM History 15 Min Bin List";
          key "bin-number";
          config false;
          description
            "PM history 15-minute bin list.";
          leaf bin-number {
            ui:ui-name "Bin Number";
            type uint32 {
              range "1..96";
            }
            description
              "The PM bin number, an index value representing the current position
               in the list of historical PM bins at the time the data is requested.
               1 is the most recent history bin, and 96 is the oldest.";
          }

          uses pm-bin-id-container;

          uses pm-history-bin-state-container;

          container statistics {
            ui:ui-name "Bin Statistics";
            config false;
            description
              "Statistics data.";
            uses pm-pg-stats-group;
          }
        }
      }

      container history-24-hour-bin {
        ui:ui-name "PM History 24 Hour Bin";
        config false;
        description
          "PM History 24-hour bin.";
        uses pm-bin-id-container;

        uses pm-history-bin-state-container;

        container statistics {
          ui:ui-name "Bin Statistics";
          config false;
          description
            "Statistics data.";
          uses pm-pg-stats-group;
        }
      }
    }
  }

  rpc waveserver-pm-clear-instance {
    description
      "Clear statistics for the specified instance.";
    input {
      leaf instance-name {
        ui:ui-name "Instance Name";
        type cienawstypes:string-maxl-32;
        description
          "Unique name for PM instance.";
      }

      leaf history {
        ui:ui-name "History";
        type boolean;
        description
          "Whether to clear history.";
      }
    }

    output {
      leaf return-code {
        type uint32;
        description
          "return code: 0 is success; non-zero is failure";
      }

      leaf return-string {
        type cienawstypes:string-maxl-254;
        description
          "Return code description";
      }
    }
  }

  rpc waveserver-pm-clear-interface {
    description
      "Clear statistics for the specified interface.";
    input {
      leaf interface-name {
        ui:ui-name "Interface Name";
        type cienawstypes:string-maxl-32;
        mandatory true;
        description
          "Interface name.";
      }

      leaf interface-type {
        ui:ui-name "Interface Type";
        type pm-interface-type;
        mandatory true;
        description
          "Interface type (PTP, Port, Channel, Slot, Protection)";
      }

      leaf profile-type {
        ui:ui-name "PM Profile Type";
        type pm-profile-type;
        description
          "The PM profile type. Can be optionally specified to clear only a
           specific profile on this interface. Not applicable to slot interface-type.";
      }

      leaf bin-type {
        ui:ui-name "PM Bin Type";
        type pm-bin-type;
        description
          "The PM bin type. Can be optionally specified to clear only a
           specific bin or history on this interface. Not applicable to slot interface-type.";
      }
    }

    output {
      leaf return-code {
        type uint32;
        description
          "return code: 0 is success; non-zero is failure";
      }

      leaf return-string {
        type cienawstypes:string-maxl-254;
        description
          "Return code description";
      }
    }
  }

  rpc waveserver-pm-clear-all {
    description
      "Clear statistics for the specified interface.";
    input {
      leaf history {
        ui:ui-name "History";
        type boolean;
        description
          "Whether to clear history.";
      }
    }

    output {
      leaf return-code {
        type uint32;
        description
          "return code: 0 is success; non-zero is failure";
      }

      leaf return-string {
        type cienawstypes:string-maxl-254;
        description
          "Return code description";
      }
    }
  }

  rpc waveserver-pm-baseline-set-all {
    description
      "Set chassis baselines.";

    output {
      leaf return-code {
        type uint32;
        description
          "return code: 0 is success; non-zero is failure";
      }

      leaf return-string {
        type cienawstypes:string-maxl-254;
        description
          "Return code description";
      }
    }
  }

  rpc waveserver-pm-baseline-set-interface {
    description
      "Set baseline for the specified interface.";
    input {
      leaf interface-name {
        ui:ui-name "Interface Name";
        type cienawstypes:string-maxl-32;
        mandatory true;
        description
          "Interface name for slot or ptp.";
      }

      leaf interface-type {
        ui:ui-name "Interface Type";
        type enumeration {
          enum "slot" {
            description
              "Slot interface.";
          }
          enum "ptp" {
            description
              "PTP interface type.";
          }
        }
        mandatory true;
        description
          "Interface type slot or ptp.";
      }

      leaf direction {
        ui:ui-name "Direction";
        type enumeration {
          enum "rx" {
            description
              "Rx direction.";
          }
          enum "tx" {
            description
              "Tx direction.";
          }
        }
        description
          "Direction for ptp baseline.";
      }
    }

    output {
      leaf return-code {
        type uint32;
        description
          "return code: 0 is success; non-zero is failure";
      }

      leaf return-string {
        type cienawstypes:string-maxl-254;
        description
          "Return code description";
      }
    }
  }

  rpc waveserver-pm-baseline-clear-all {
    description
      "Clear chassis baselines.";

    output {
      leaf return-code {
        type uint32;
        description
          "return code: 0 is success; non-zero is failure";
      }

      leaf return-string {
        type cienawstypes:string-maxl-254;
        description
          "Return code description";
      }
    }
  }

  rpc waveserver-pm-baseline-clear-interface {
    description
      "Clear baseline for the specified interface.";
    input {
      leaf interface-name {
        ui:ui-name "Interface Name";
        type cienawstypes:string-maxl-32;
        mandatory true;
        description
          "Interface name for slot or ptp.";
      }

      leaf interface-type {
        ui:ui-name "Interface Type";
        type enumeration {
          enum "slot" {
            description
              "Slot interface.";
          }
          enum "ptp" {
            description
              "PTP interface type.";
          }
        }
        mandatory true;
        description
          "Interface type slot or ptp.";
      }

      leaf direction {
        ui:ui-name "Direction";
        type enumeration {
          enum "rx" {
            description
              "Rx direction.";
          }
          enum "tx" {
            description
              "Tx direction.";
          }
        }
        description
          "Direction for ptp baseline.";
      }
    }

    output {
      leaf return-code {
        type uint32;
        description
          "return code: 0 is success; non-zero is failure";
      }

      leaf return-string {
        type cienawstypes:string-maxl-254;
        description
          "Return code description";
      }
    }
  }

  rpc waveserver-pm-tca-admin-state-set-interface {
    description
      "Set adminState for the specified interface.";
    input {
      leaf interface-name {
        ui:ui-name "Interface Name";
        type cienawstypes:string-maxl-32;
        mandatory true;
        description
          "Interface name for slot or ptp or port or channel.";
      }

      leaf interface-type {
        ui:ui-name "Interface Type";
        type enumeration {
          enum "slot" {
            description
              "Slot interface.";
          }
          enum "ptp" {
            description
              "PTP interface type.";
          }
          enum "port" {
            description
              "Port interface type.";
          }
          enum "channel" {
            description
              "Channel interface type.";
          }
          enum "protection" {
            description
              "Protection-Group interface type.";
          }
        }
        mandatory true;
        description
          "Interface type.";
      }

      leaf tca-admin-state {
        ui:ui-name "TCA Admin State";
        type cienawstypes:enabled-disabled-enum;
        description
          "The TCA administrative state for this interface.";
      }
    }

    output {
      leaf return-code {
        type uint32;
        description
          "return code: 0 is success; non-zero is failure";
      }

      leaf return-string {
        type cienawstypes:string-maxl-254;
        description
          "Return code description";
      }
    }
  }
}
