module ciena-waveserver-system {
  namespace "urn:ciena:params:xml:ns:yang:ciena-ws:ciena-waveserver-system";
  prefix system;

  import yuma-ncx {
    prefix ncx;
  }

  import ciena-waveserver-typedefs {
    prefix cienawstypes;
  }

  import ietf-inet-types {
    prefix inet;
  }

  import ciena-ui {
    prefix ui;
  }

  organization
    "Ciena Corporation";
  contact
    "Web URL: http://www.ciena.com/
     Postal:  7035 Ridge Road
             Hanover, Maryland 21076
             U.S.A.
     Phone:   +1 800-921-1144
     Fax:     +1 410-694-5750";
  description
    "This YANG module defines Ciena's Waveserver System representation.";

  revision 2023-08-11 {
    description
      "Added 'waveserver-system-client-config-dhcp-lease-renew' RPC.
       Added 'dhcpv6' sub-container under 'client-config' containers.
       Added 'grpc' container under 'client-config' for dial-out trusted-dns configuration.";
    reference
      "Waveserver OS R2.5.0 user's guide.";
  }
  revision 2023-08-10 {
    description
      "Added 'craft-gui-admin-state' leaf to waveserver-system.
       Added 'fully-qualified-domain-name' leaf to waveserver-system-domain-name.";
    reference
      "Waveserver OS R2.4.5 user's guide.";
  }
  revision 2023-01-16 {
    description
      "Added 'exclude-corefiles' leaf to waveserver-system-state-dump rpc.
       Added 'exclude-corefiles' leaf to waveserver-system-state-dump container.";
    reference
      "Waveserver OS R2.2.9 user's guide.";
  }
  revision 2022-11-30 {
    description
      "Added 'openconfig' and 'caching' containers under system-management container.
       Added 'netconf' container under server-config container.
       Moved 'admin-state' leaf to new 'netconf' container.
       Added 'candidate-advertisement' leaf to new 'netconf' container.
       Added 'remote-management-auto-enable' leaf to 'default-settings' container.
       Added 'operational-priority' leaf to 'dns/server' container.";
    reference
      "Waveserver OS R2.4 user's guide.";
  }
  revision 2022-08-25 {
    description
      "Added ntp-key/key-type 'SHA1'.
       Added 'sha1key-authentication-state' leaf to ntp container.
       Added 'waveserver-system-ntp-sha1auth-import' rpc.
       Changed ntp-key/key-type/key-value string length from 1..31 to 1..40.
       Enabled config of ntp-key/key-type.";
    reference
      "Waveserver OS R2.3.11 user's guide.";
  }
  revision 2022-04-26 {
    description
      "Added ssh client-key section for SSH Client Key Auth,
            typedef: 'ssh-client-key-type-enum', 'ssh-client-key-status-enum',
            container: 'ssh/client-key',
            rpcs: 'ssh-client-generate-key', 'ssh-client-transfer-public-key',
                  'ssh-client-delete-key'.";
    reference
      "Waveserver-AI R2.2.0 user's guide.";
  }
  revision 2022-04-14 {
    description
      "Modified auto-config-recovery passphrase size from 128 to 256.
       Added 'shell' container under environment container.
       modified 'encryption-only' leaf from read-only to read-write.";
    reference
      "Waveserver OS R2.3.1 user's guide.";
  }
  revision 2021-08-25 {
    description
      "Renamed the 'waveserver-system-https-server-rsa-regenerate' rpc to 'waveserver-system-tls-rsa-generate'.";
    reference
      "Waveserver OS R2.2 user's guide.";
  }
  revision 2021-06-11 {
    description
      "Deprecated and moved the shell/inactivity-timer and shell/inactivity-timeout leafs to the 'server-config' container.
       Updated range for https/inactivity-timeout to match global-inactivity-timeout range 1..1500 minutes.
       Removed obsolete reset-to-factory-default-button leaf.
       Updated enum values for client-config/dns/server/source leaf.
       Updated max length for 'url' string type to 512 characters.
       Removed deprecated 'include-corefiles' leaf in RPC waveserver-system-state-dump.
       Added 'remote-url' leaf to waveserver-system-putfile and waveserver-system-getfile RPCs.
       Added 'url' leaf to 'waveserver-system-ssh-server-generate-key' and 'waveserver-system-ssh-server-install-key' RPCs.
       Added 'options-data' container to client-config/dhcp.
       Added 'state-dump' container.
       Added 'gnmi' management interface query-limits support.
       Added 'root-scope' management interface attributes support.
       Increased the string length of passphrase to 128.
       Added 'terrestrial-reach-limit' leaf to 'default-settings' container.
       Obsoleted waveserver-system-https-server-rsa-activate-p12-file rpc.
       Removed the mandatory flag from the user leaf in waveserver-system-ssh-server-delete-key rpc's input.
       Added 'certificate-verification' container to 'grpc' container.
       Removed 'mutual-authentication-state' leaf from 'grpc' container.
       Removed 'config-file-crc', 'backup-file-crc', 'chassis-serial-number', 'cp-serial-number', 'ap-backup-directory' from 'auto-config-recovery' container.
       Modified 'time-offset' leaf type from decimal to int32.
       Added 'waveserver-system-set-date-time' rpc.
       Removed 'time' and 'date' leafs from time-config-attributes.";
    reference
      "Waveserver OS R2.1 user's guide.";
  }
  revision 2020-10-28 {
    description
      "Add leaf 'admin-state' to 'auto-config-recovery' container.
       Add leaf 'passphrase' to 'auto-config-recovery' container.
       Add leaf 'audit-interval' to 'auto-config-recovery' container.
       Add leaf 'operational-state' to 'auto-config-recovery' container.
       Add leaf 'last-backup-reason' to 'auto-config-recovery' container.
       Add leaf 'time-of-last-backup' to 'auto-config-recovery' container.
       Add leaf 'time-of-last-audit' to 'auto-config-recovery' container.
       Add leaf 'config-file-crc' to 'auto-config-recovery' container.
       Add leaf 'backup-file-crc' to 'auto-config-recovery' container.
       Add leaf 'chassis-serial-number' to 'auto-config-recovery' container.
       Add leaf 'cp-serial-number' to 'auto-config-recovery' container.
       Add leaf 'ap-backup-directory' to 'auto-config-recovery' container.
       Add 'rpc waveserver-system-auto-config-force-backup'.";
    reference
      "Waveserver OS R2.0.3 user's guide.";
  }
  revision 2020-02-29 {
    description
      "Add query limits for PM history bin GET operations.
       Deprecated 'include-corefiles' in RPC waveserver-system-state-dump.
       Add 'container auto-config-recovery'.
       Add 'rpc waveserver-system-override-config-mismatch'.";
    reference
      "Waveserver OS R2.0.0 user's guide.";
  }
  revision 2019-06-04 {
    description
      "Add grouping: network-id-config-group.
       Add container network under container id.";
    reference
      "Waveserver Ai R1.5 user's guide.";
  }
  revision 2019-03-07 {
    description
      "Added cluster-enrollment attribute to indicate of the enrollment
       status of the waveserver in the cluster.
       Groupify the module for inclusion into the ciena-waveserver-cluster module.
       Added cluster-role attribute to define the role of the member node in
       cluster.
       Added typedef: 'dhcp-state-enum'.
       Added leafs: 'dhcp/interface-type','dhcp/dhcp-state',
            'dhcp/discovery-interval','dhcp/requested-lease-time',
            'dhcp/lease-time','dhcp/lease-remaining',
            'dhcp/renewal-time','dhcp/renewal-remaining',
            'dhcp/rebinding-time','dhcp/rebinding-remaining',
            'dhcp/dhcp-server'.
       Added 'options' sub-container to the 'client-config/dhcp' container.
       Added leafs for DHCP client options.
       Added 'waveserver-system-client-config-dhcp-lease-renew' RPC.
       Added 'url' input parameter leaf in 'waveserver-system-state-dump' RPC.
       Added 'list multicast-server' to container 'ntp'.
       Changed 'dns/server/ip-address' type from 'ipv4-address' to 'ip-address'.
       Added 'environment/diag' container.
       Added new RPC call (waveserver-system-client-config-ntp-md5auth-import)
             for NTP MD5 auth key import file.";
    reference
      "Waveserver Ai R1.4 user's guide.";
  }
  revision 2018-10-09 {
    description
      "Added typedef: 'ssh-key-type-enum', 'ssh-key-generation-status-enum',
            'ssh-public-key-user-status-enum', and
            'ssh-public-key-user-account-error-status-enum'.
       Added grouping: 'common-ocsp-group'.
       Added container: 'ssl'.
       Added containers: 'server-config/ssh/algorithms', 'server-config/ssh/key'.
       Added container: 'server-config/https', 'server-config/grpc'.
       Deprecated leaf: 'server-config/web-server-state, replaced with 'admin-state'
            in https container.
       Deprecated leaf: 'server-config/grpc-server-state, replaced with 'admin-state'
            in grpc container.
       Added leafs: 'client-config/ntp/autokey-authentication-state',
            'client-config/ntp/autokey-certificate-present',
            'client-config/ntp/autokey-type',
            'client-config/ntp/autokey-signature-algorithm',
            'client-config/ntp/autokey-valid-from',
            'client-config/ntp/autokey-valid-to',
            'client-config/ntp/server/autokey-authentication'.
       Added RPCs: 'waveserver-system-https-server-rsa-activate-p12-file',
            'waveserver-system-https-server-rsa-regenerate',
            'waveserver-system-ssh-server-activate-host-key',
            'waveserver-system-ssh-server-delete-key',
            'waveserver-system-ssh-server-generate-key',
            'waveserver-system-ssh-server-install-key',
            'waveserver-system-ntp-generate-autokey'.
       Added several leafs to the 'shell' container.
       Added container: 'lamp-test'.
       Updated 'environment/root/secret' to be writable (config true).
       Added 'encryption-only' read-only leaf to the 'global-provisioning' container.
       Obsolete leaf: 'global-provisioning/reset-to-factory-defaults',
            not supported on Waveserver Ai.";
    reference
      "Waveserver Ai R1.3 user's guide.";
  }
  revision 2018-06-04 {
    description
      "Added ncx:password statements to password leafs.
       Added 'dns' sub-container to the 'client-config' container.
       Added 'waveserver-system-dns-resolve-ip' RPC.
       Made 'file-name' input parameter mandatory in 'waveserver-system-state-dump' RPC.
       Added 'reachable', 'authenticated', and 'server-condition' leafs to the ntp server list.";
    reference
      "Waveserver Ai R1.2 user's guide.";
  }
  revision 2018-01-04 {
    description
      "Changed site 'latitude' and 'longitude' precision from 5 to 6 digits.
       Updated 'server-config' attribute permissions.
       Added 'domain-name' container support.
       Added 'server-config/ssh' container support.
       Added 'client-config' container support with 'dhcp' and 'ntp' sub-containers.
       Added 'shell' container for Waveserver CLI shell/session configuration attributes.
       Added 'secret' read-only attribute to the environment/root container.
       Remove 'include-datapath' and 'include-optics' attributes from 'state-dump' command.";
    reference
      "Waveserver Ai R1.1 user's guide.";
  }
  revision 2017-06-30 {
    description
      "Waveserver Platform Data Model
       Migrated from Waveserver Classic R1.4 YANG model.
       Updated namespace to 'ciena-waveserver'.
       Added scp server support (from WS 1.5).
       Remove bandplan, front-display, fcs-error-forwarding, low-power-mode as not supported
       on WS Ai R1.0.
       Updated xftp-config/tftp 'dhcp-host-name' and 'current-host-name' to be config false.
       Added 'default-settings' container with leafs to configure 'conditioning-type'
       and 'conditioning-holdoff' system defaults.
       Added 'grpc-server-state' and 'scp-server-state' to server-config container.
       Combined several boolean leafs in 'server-settings-group' into a single enum.";
    reference
      "Waveserver Ai R1.0 user's guide.";
  }

  typedef cluster-role-enum {
    type enumeration {
      enum "member" {
        description
          "Member (which is default).";
      }
      enum "primary" {
        description
          "Primary manager.";
      }
    }
    description
      "Enumeration definition for cluster-role.";
  }

  typedef dhcp-state-enum {
    type enumeration {
      enum "disabled" {
        description
          "Disabled State.";
      }
      enum "init" {
        description
          "Initializing.";
      }
      enum "selecting" {
        description
          "Got answers. Selecting server to query.";
      }
      enum "requesting" {
        description
          "Send DHCPREQUEST. Goto BOUND when DHCPACK is received.";
      }
      enum "bound" {
        description
          "Got IP address from server. Waiting for LeaseTime to expire.";
      }
      enum "renewing" {
        description
          "Lease time T1 has expired. Trying to extend IP address lease.";
      }
      enum "rebinding" {
        description
          "Lease time T2 has expired. Trying to extend IP lease from any server.";
      }
      enum "inform" {
        description
          "Interface has an IP address. Inform the server of the IP number.";
      }
      enum "rebooting" {
        description
          "Rebooting.";
      }
    }
    description
      "DHCP state type.";
  }

  typedef dhcpv6-state-enum {
    type enumeration {
      enum "disabled" {
        description
          "Disabled State.";
      }
      enum "preinit" {
        description
          "Initializing.";
      }
      enum "bound" {
        description
          "Got IP address from server. Waiting for LeaseTime to expire.";
      }
      enum "renewing" {
        description
          "Lease time T1 has expired. Trying to extend IP address lease.";
      }
      enum "rebinding" {
        description
          "Lease time T2 has expired. Trying to extend IP lease from any server.";
      }
      enum "deprecated" {
        description
          "Lease renewal didn't occur beyond the preferred lease life time. use of the address is discouraged";
      }
      enum "expired" {
        description
          "IP address lease expired.";
      }
    }
    description
      "DHCPv6 state type.";
  }

  typedef ssh-key-type-enum {
    type enumeration {
      enum "unknown" {
        description
          "Unknown key.";
      }
      enum "rsa2048" {
        description
          "RSA key with size of 2048 bits.";
      }
      enum "rsa3072" {
        description
          "RSA key with size of 3072 bits.";
      }
      enum "rsa4096" {
        description
          "RSA key with size of 4096 bits.";
      }
      enum "ecdsa256" {
        description
          "ECDSA key with size of 256 bits.";
      }
      enum "ecdsa384" {
        description
          "ECDSA key with size of 384 bits.";
      }
      enum "ecdsa521" {
        description
          "ECDSA key with size of 521 bits.";
      }
    }
    description
      "Enum for SSH key type.";
  }

  typedef ssh-key-generation-status-enum {
    type enumeration {
      enum "invalid" {
        value 0;
        description
          "Invalid result.";
      }
      enum "generating" {
        value 1;
        description
          "The key is being generated.";
      }
      enum "generated" {
        value 2;
        description
          "The key has been generated.";
      }
      enum "failure" {
        value 3;
        description
          "The key generation failed.";
      }
    }
    description
      "The result of the SSH key generation.";
  }

  typedef ssh-public-key-user-status-enum {
    type enumeration {
      enum "installed" {
        description
          "The public key for the user has been installed.";
      }
      enum "invalid" {
        description
          "The public key for the user is invalid.";
      }
    }
    description
      "The status of the public key authentication for the user.";
  }

  typedef ssh-public-key-user-account-error-status-enum {
    type enumeration {
      enum "none" {
        description
          "No error.";
      }
      enum "not-created" {
        description
          "The user account is not created.";
      }
      enum "no-password" {
        description
          "The user account has no password.";
      }
      enum "key-type-not-supported" {
        description
          "The public key type for the user is not supported.";
      }
    }
    description
      "The error status for the user account that uses public key authentication.";
  }

  typedef ssh-client-key-type-enum {
    type enumeration {
      enum "unknown" {
        description
          "Unknown key.";
      }
      enum "rsa2048" {
        description
          "RSA key with size of 2048 bits.";
      }
      enum "rsa3072" {
        description
          "RSA key with size of 3072 bits.";
      }
      enum "rsa4096" {
        description
          "RSA key with size of 4096 bits.";
      }
    }
    description
      "Enum for SSH client key type.";
  }

  typedef ssh-client-key-status-enum {
    type enumeration {
      enum "empty" {
        description
          "SSH client key does not exist.";
      }
      enum "valid" {
        description
          "SSH client key exists and is valid.";
      }
      enum "error" {
        description
          "SSH client key exists, but is not valid.";
      }
    }
    description
      "The status of SSH client key authentication.";
  }

  typedef line-protection-enum {
    type enumeration {
      enum "unprotected" {
        value 0;
        description
          "Line protection is disabled.";
      }
      enum "trunk-ops" {
        value 1;
        description
          "Line protection is enabled.";
      }
    }
    description
      "Enum for line protection options.";
  }

  typedef root-scope-enum {
    type enumeration {
      enum "native" {
        description
          "Native models only, specifically the ciena-waveserver and ciena-pro models.";
      }
      enum "openconfig" {
        description
          "Openconfig models only.";
      }
      enum "all" {
        description
          "All models.";
      }
    }
    description
      "Defines the scope of data models to include in root-level operations.";
  }

  grouping network-id-config-group {
    description
      "Grouping for Waveserver system network identification
       attributes.";
    leaf id {
      ui:ui-name "Network Identifier";
      type uint8 {
        range "0..254";
      }
      description
        "An integer to uniquely identify the sub-network domain in which this
         Waveserver chassis is managed.";
    }

    leaf name {
      ui:ui-name "Network Name";
      type string {
        length "0..32";
      }
      description
        "A name for the sub-network domain.";
    }

    leaf description {
      ui:ui-name "Network Description";
      type string {
        length "0..64";
      }
      description
        "A description for the sub-network domain.";
    }
  }

  grouping site-id-config-group {
    description
      "Grouping for Waveserver system site identification attributes.";
    leaf id {
      ui:ui-name "Site Identifier";
      type uint16 {
        range "0..65535";
      }
      description
        "An integer to uniquely identify the site where this Waveserver is
         located. This is used to help group Waveservers together with line
         system equipment. All equipment in a common site should share the
         same site identifier. ";
    }

    leaf name {
      ui:ui-name "Site Name";
      type string {
        length "0..32";
      }
      description
        "The name for the site where the Waveserver is located.";
    }

    leaf description {
      ui:ui-name "Site Description";
      type string {
        length "0..64";
      }
      description
        "The site description";
    }

    leaf latitude {
      ui:ui-name "Latitude";
      type decimal64 {
        fraction-digits 6;
        range "-90.0 .. 90.0";
      }
      description
        "Geographic coordinate for the site location in degrees.";
    }

    leaf longitude {
      ui:ui-name "Longitude";
      type decimal64 {
        fraction-digits 6;
        range "-180.0 .. 180.0";
      }
      description
        "Geographic coordinate for the site location in degrees.";
    }

    leaf address {
      ui:ui-name "Site Address";
      type string {
        length "0..128";
      }
      description
        "The street address of the site.";
    }
  }

  grouping group-id-config-group {
    description
      "Grouping for Waveserver system group (or cluster) identification
       attributes.";
    leaf id {
      ui:ui-name "Group Identifier";
      type uint8 {
        range "0..99";
      }
      description
        "An integer to uniquely identify a group of Waveservers within a
         site.";
    }

    leaf name {
      ui:ui-name "Group Name";
      type string {
        length "0..32";
      }
      description
        "A name for the group of Waveservers.";
    }

    leaf description {
      ui:ui-name "Group Description";
      type string {
        length "0..64";
      }
      description
        "A description for the group of Waveservers. ";
    }
  }

  grouping xftp-config-group {
    description
      "Grouping for Waveserver system XFTP configuration attributes.";
    leaf mode {
      ui:ui-name "XFTP mode";
      type enumeration {
        enum "none" {
          value 0;
          description
            "No FTP mode is specified.";
        }
        enum "tftp" {
          value 1;
          description
            "Trivial File Transfer Protocol (TFTP) mode.";
        }
        enum "ftp" {
          value 2;
          description
            "File Transfer Protocol (FTP) mode.";
        }
        enum "sftp" {
          value 3;
          description
            "Secure File Transfer Protocol (SFTP) mode.";
        }
        enum "scp" {
          value 4;
          description
            "Secure Copy Protocol (SCP) mode.";
        }
      }
      description
        "Identifies which file transfer protocol to user when default-server
         is specified in a command - FTP, SFTP, TFTP or SCP.";
    }

    container tftp {
      ui:ui-name "TFTP";
      description
        "Waveserver system TFTP configuration.";
      leaf config-host-name {
        ui:ui-name "TFTP Config Host Name";
        type cienawstypes:string-maxl-64;
        description
          "TFTP host name configured by user. Format is an IP address (with
           optional port) or host name.";
      }

      leaf dhcp-host-name {
        ui:ui-name "TFTP DHCP Host Name.";
        type cienawstypes:string-maxl-64;
        config false;
        description
          "TFTP DHCP host name.";
      }

      leaf current-host-name {
        ui:ui-name "TFTP Current Host Name";
        type cienawstypes:string-maxl-64;
        config false;
        description
          "TFTP current host name.";
      }
    }

    container ftp {
      ui:ui-name "FTP";
      description
        "Waveserver system FTP configuration.";
      leaf host-name {
        ui:ui-name "FTP Host Name";
        type cienawstypes:string-maxl-64;
        description
          "FTP host name. Format is an IP address (with optional port) or
           host name.";
      }

      leaf user-name {
        ui:ui-name "FTP User Name.";
        type cienawstypes:string-maxl-32;
        description
          "FTP user name.";
      }

      leaf password {
        ui:ui-name "FTP Password";
        ncx:password;
        type cienawstypes:string-maxl-128;
        description
          "FTP password string.";
      }

      leaf secret {
        ui:ui-name "FTP Secret";
        type cienawstypes:string-maxl-256;
        description
          "FTP secret string.";
      }
    }

    container sftp {
      ui:ui-name "SFTP";
      description
        "Waveserver system SFTP configuration.";
      leaf host-name {
        ui:ui-name "SFTP Host Name";
        type cienawstypes:string-maxl-64;
        description
          "SFTP host name. Format is an IP address (with optional port) or
           host name.";
      }

      leaf user-name {
        ui:ui-name "SFTP User Name.";
        type cienawstypes:string-maxl-32;
        description
          "SFTP user name.";
      }

      leaf password {
        ui:ui-name "SFTP Password";
        ncx:password;
        type cienawstypes:string-maxl-128;
        description
          "SFTP password string.";
      }

      leaf secret {
        ui:ui-name "SFTP Secret";
        type cienawstypes:string-maxl-256;
        description
          "SFTP secret string.";
      }
    }

    container scp {
      ui:ui-name "SCP";
      description
        "Waveserver system SCP configuration.";
      leaf host-name {
        ui:ui-name "SCP Host Name";
        type cienawstypes:string-maxl-64;
        description
          "SCP host name. Format is an IP address (with optional port) or
           host name.";
      }

      leaf user-name {
        ui:ui-name "SCP User Name.";
        type cienawstypes:string-maxl-32;
        description
          "SCP user name.";
      }

      leaf password {
        ui:ui-name "SCP Password";
        ncx:password;
        type cienawstypes:string-maxl-128;
        description
          "SCP password string.";
      }

      leaf secret {
        ui:ui-name "SCP Secret";
        type cienawstypes:string-maxl-256;
        description
          "SCP secret string.";
      }
    }
  }

  grouping time-config-attributes {
    description
      "Grouping definition for Waveserver System time configuration attributes.";
    leaf time-offset {
      ui:ui-name "Time Offset";
      type int32 {
        range "-43200 .. 50400";
      }
      description
        "System time-offset from UTC in seconds.";
    }

    leaf time-stamp {
      ui:ui-name "Time Stamp";
      type enumeration {
        enum "utc" {
          description
            "Timestamp is indicated in Coordinated Universal Time (UTC) format.";
        }
        enum "local" {
          description
            "Timestamp is indicated in local time format.";
        }
      }
      description
        "System time stamp format: local time or UTC time.";
    }

    leaf local-date-time {
      ui:ui-name "Local Date and Time";
      type string {
        length "1..41";
      }
      config false;
      description
        "Local date and time.";
    }

    leaf coordinated-universal-time {
      ui:ui-name "Coordinated Universal Time.";
      type string {
        length "1..41";
      }
      config false;
      description
        "UTC date and time in 'YYYY-MM-DDTHH:MM:SS' format.'";
    }

    leaf system-uptime {
      ui:ui-name "System Uptime";
      type string {
        length "1..17";
      }
      config false;
      description
        "Time since last reboot, in format: xxxd xxh xxm xxs";
    }
  }

  grouping server-settings-group {
    description
      "Grouping for common server settings attributes used in various RPCs.";
    leaf server-to-use {
      type enumeration {
        enum "none" {
          description
            "Don't specify a remote server for the file transfer. Either use
             local file (if applicable) or url formatted input.";
        }
        enum "default-server" {
          description
            "Use the configured system default server for the file transfer.
             Default server type is configured in /waveserver-system/xftp-config/mode.";
        }
        enum "default-tftp-server" {
          description
            "Use the configured system default TFTP server for the file transfer.
             Configured in /waveserver-system/xftp-config/tftp.";
        }
        enum "default-ftp-server" {
          description
            "Use the configured system default FTP server and credentials for
             the file transfer. Configured in /waveserver-system/xftp-config/ftp.";
        }
        enum "default-sftp-server" {
          description
            "Use the configured system default SFTP server and credentials for
             the file transfer. Configured in /waveserver-system/xftp-config/sftp.";
        }
        enum "default-scp-server" {
          description
            "Use the configured system default SCP server and credentials for
             the file transfer. Configured in /waveserver-system/xftp-config/scp.";
        }
        enum "specified-tftp-server" {
          description
            "Use the user-specified TFTP server for the file transfer.
             A tftp-server value must also be specified in the request.";
        }
        enum "specified-ftp-server" {
          description
            "Use the user-specified FTP server for the file transfer.
             An ftp-server value must also be specified in the request.";
        }
        enum "specified-sftp-server" {
          description
            "Use the user-specified SFTP server for the file transfer.
             An sftp-server value must also be specified in the request.";
        }
        enum "specified-scp-server" {
          description
            "Use the user-specified SCP server for the file transfer.
             A scp-server value must also be specified in the request.";
        }
      }
      description
        "If server-to-use is specified with a value other than 'none; in the
         RPC request, then the system will use the specified server for the
         file transfer.";
    }

    leaf tftp-server-address {
      ui:ui-name "TFTP Server IP Address";
      type cienawstypes:string-maxl-64;
      description
        "The TFTP server IP address to use for the file transfer if
         server-to-use is 'specified-tftp-server'. Otherwise this attribute
         is ignored.";
    }

    leaf ftp-server-address {
      ui:ui-name "FTP Server IP Address";
      type cienawstypes:string-maxl-64;
      description
        "The FTP server IP address to use for the file transfer if
         server-to-use is 'specified-ftp-server'. Otherwise this attribute
         is ignored.";
    }

    leaf ftp-login-id {
      ui:ui-name "FTP Login ID";
      type cienawstypes:string-maxl-32;
      description
        "The FTP username.";
    }

    leaf ftp-password {
      ui:ui-name "FTP Password";
      type cienawstypes:string-maxl-128;
      description
        "The FTP password.";
    }

    leaf ftp-secret {
      ui:ui-name "FTP Secret";
      type cienawstypes:string-maxl-256;
      description
        "The FTP secret(pre-encrypted) string.";
    }

    leaf sftp-server-address {
      ui:ui-name "SFTP Server IP Address";
      type cienawstypes:string-maxl-64;
      description
        "The SFTP server IP address to use for the file transfer if
         server-to-use is 'specified-sftp-server'. Otherwise this attribute
         is ignored.";
    }

    leaf sftp-login-id {
      ui:ui-name "SFTP Login ID";
      type cienawstypes:string-maxl-32;
      description
        "The SFTP login ID.";
    }

    leaf sftp-password {
      ui:ui-name "SFTP Password";
      type cienawstypes:string-maxl-128;
      description
        "The SFTP password.";
    }

    leaf sftp-secret {
      ui:ui-name "SFTP Secret";
      type cienawstypes:string-maxl-256;
      description
        "The SFTP secret(pre-encrypted) string.";
    }

    leaf scp-server-address {
      ui:ui-name "SCP Server IP Address";
      type cienawstypes:string-maxl-64;
      description
        "The SCP server IP address to use for the file transfer if
         server-to-use is 'specified-scp-server'. Otherwise this attribute
         is ignored.";
    }

    leaf scp-login-id {
      ui:ui-name "SCP Login ID";
      type cienawstypes:string-maxl-32;
      description
        "The SCP login ID.";
    }

    leaf scp-password {
      ui:ui-name "SCP Password";
      type cienawstypes:string-maxl-128;
      description
        "The SCP password.";
    }

    leaf scp-secret {
      ui:ui-name "SCP Secret";
      type cienawstypes:string-maxl-256;
      description
        "The SCP secret(pre-encrypted) string.";
    }
  }

  grouping common-ocsp-group {
    description
      "Grouping of common attributes for Online Certificate Status
       Protocol (OCSP) configuration.";
    leaf admin-state {
      ui:ui-name "OCSP Admin State";
      type cienawstypes:enabled-disabled-enum;
      description
        "Whether OCSP verification is enabled or disabled.";
    }

    leaf responder-preference {
      ui:ui-name "Responder Preference";
      type enumeration {
        enum "aia" {
          description
            "Responder in Authority Information Access(AIA) extension is
             used first.";
        }
        enum "default-responder" {
          description
            "The default responder is used first.";
        }
      }
      description
        "If 'responder-preference' is set to aia, the OCSP responder
         referred in client certificate AIA extension will be used first
         during OCSP certificate validation.
         If it is set to 'default-responder', the configured default
         OCSP responder is used first.";
    }

    leaf default-responder {
      ui:ui-name "Default Responder";
      type cienawstypes:string-maxl-128;
      description
        "Default OCSP responder. It should be in URL format.
         e.g. https://192.168.20.2:2440. If the 'responder-preference'
         is not set to 'default-responder', the URL given will be used
         only if no responder URL (AIA extension) is specified in the
         client certificate being verified.";
    }

    leaf nonce {
      ui:ui-name "Nonce";
      type cienawstypes:on-off-enum;
      description
        "Determine whether queries to OCSP responders should contain a
         nonce or not. By default nonce option is turned on.";
    }
  }

  grouping waveserver-system-group {
    ui:ui-name "System";
    description
      "Waveserver System configuration data and operational data.";
    container id {
      ui:ui-name "Identification";
      description
        "Waveserver system identification attributes.";
      container network {
        ui:ui-name "Network";
        description
          "Waveserver system network attributes.";
        uses network-id-config-group;
      }

      container site {
        ui:ui-name "Site";
        description
          "Waveserver system site attributes.";
        uses site-id-config-group;
      }

      container group {
        ui:ui-name "Group";
        description
          "Waveserver system group attributes.";
        uses group-id-config-group;
      }

      container member {
        ui:ui-name "Member";
        description
          "Waveserver system member attributes.";
        leaf id {
          ui:ui-name "Member Identifier";
          type uint8 {
            range "0..254";
          }
          description
            "An integer to uniquely identify a Waveserver chassis within a
             group of Waveservers.";
        }

        leaf name {
          ui:ui-name "Member Name";
          type string {
            length "0..64";
          }
          description
            "A name for the Waveserver chassis. Set to the host name by default.";
        }

        leaf description {
          ui:ui-name "Member Description";
          type string {
            length "0..64";
          }
          description
            "A description for the Waveserver chassis.";
        }

        leaf frame-identification {
          ui:ui-name "Member Frame Identification";
          type string {
            length "0..128";
          }
          description
            "A description to identify the location of the Waveserver chassis
             within the data center. For example, the building, floor, aisle,
             frame number, etc.";
        }

        leaf rack-unit-number {
          ui:ui-name "Rack Unit Number";
          type uint8 {
            range "0..50";
          }
          description
            "A logical identifier for the location of the Waveserver within the
             frame or rack. For example, the device at the top could be labeled
             unit 1.";
        }

        leaf cluster-role {
          ui:ui-name "Cluster-Role";
          type cluster-role-enum;
          config false;
          description
            "Attribute indicating the role of this node in the cluster. Default
             value is member.";
        }

        leaf cluster-enrollment {
          ui:ui-name "Cluster-Enrollment";
          type cienawstypes:enabled-disabled-enum;
          description
            "Attribute indicating if the waveserver member is enrolled into culster.";
        }
      }
    }

    container host-name {
      ui:ui-name "Host name";
      description
        "Waveserver system host name attributes.";
      leaf current-host-name {
        ui:ui-name "Hostname";
        type cienawstypes:string-maxl-64;
        config false;
        description
          "Current host name.";
      }

      leaf config-host-name {
        ui:ui-name "Hostname-Config";
        type cienawstypes:string-maxl-64;
        description
          "User configured host name.";
      }

      leaf dhcp-host-name {
        ui:ui-name "DHCP Host Name";
        type cienawstypes:string-maxl-64;
        config false;
        description
          "DHCP configured host name.";
      }
    }

    container domain-name {
      ui:ui-name "Domain Name";
      description
        "Waveserver system domain name attributes.";
      leaf current-domain-name {
        ui:ui-name "Current Domain Name";
        type cienawstypes:string-maxl-64;
        config false;
        description
          "Current domain name. This will either be the DHCP-assigned domain
           name, or the user-configured value, respectively.";
      }

      leaf config-domain-name {
        ui:ui-name "Config Domain Name";
        type cienawstypes:string-maxl-64;
        description
          "User configured domain name.";
      }

      leaf dhcp-domain-name {
        ui:ui-name "DHCP Domain Name";
        type cienawstypes:string-maxl-64;
        config false;
        description
          "DHCP configured domain name, if assigned. DHCP Client must be
           enabled with Option 15 support in order to obtain a domain name
           from the server.";
      }

      leaf fully-qualified-domain-name {
        ui:ui-name "Fully Qualified Domain Name";
        type cienawstypes:string-maxl-128;
        config false;
        description
          "Waveserver fully-qualified-domain-name, which is host-name plus
           current domain name, if both names are configured,
           otherwise it's empty.";
      }
    }

    container time-config {
      ui:ui-name "Time Configuration";
      description
        "Waveserver system time configuration attributes.";
      uses time-config-attributes;
    }

    container server-config {
      ui:ui-name "Server Configuration";
      description
        "Waveserver system server configuration attributes.";
      leaf sftp-server-state {
        ui:ui-name "SFTP Server State";
        type cienawstypes:enabled-disabled-enum;
        description
          "Indicate whether SFTP server is enabled.";
      }

      leaf scp-server-state {
        ui:ui-name "SCP Server State";
        type cienawstypes:enabled-disabled-enum;
        description
          "Indicate whether SCP server is enabled.";
      }

      leaf web-server-state {
        ui:ui-name "Web Server State";
        type cienawstypes:enabled-disabled-enum;
        status deprecated;
        description
          "Indicate whether web server is enabled, HTTPS only.
           This leaf is deprecated, replaced by admin-state in https container.";
      }

      leaf netconf-server-state {
        ui:ui-name "Netconf Server State";
        type cienawstypes:enabled-disabled-enum;
        status deprecated;
        description
          "Indicate whether NETCONF server is enabled.";
      }

      leaf restconf-server-state {
        ui:ui-name "RESTCONF Server State";
        type cienawstypes:enabled-disabled-enum;
        config false;
        description
          "Indicate whether RESTCONF server is enabled, HTTPS only.";
      }

      leaf grpc-server-state {
        ui:ui-name "gRPC Server State";
        type cienawstypes:enabled-disabled-enum;
        status deprecated;
        description
          "Indicate whether gRPC server is enabled.
           This leaf is deprecated, replaced by admin-state in grpc container.";
      }

      leaf global-inactivity-timer {
        ui:ui-name "Global Inactivity Timer";
        type cienawstypes:enabled-disabled-enum;
        description
          "Global session inactivity timer state.";
      }

      leaf global-inactivity-timeout {
        ui:ui-name "Inactivity Timeout";
        type uint16 {
          range "1..1500";
        }
        units "minutes";
        description
          "Global session inactivity timeout period, in minutes. Can be
           overridden by specific server type settings, if applicable.";
      }

      container https {
        ui:ui-name "HTTPS Server";
        description
          "HTTPS server configuration.";
        leaf admin-state {
          ui:ui-name "HTTPS Server Admin State";
          type cienawstypes:enabled-disabled-enum;
          description
            "HTTPS server administrative state.";
        }

        leaf web-ui-file-transfer-admin-state {
          ui:ui-name "Web Ui File Transfer Admin State";
          type cienawstypes:enabled-disabled-enum;
          description
            "Web Ui File Transfer administrative state.";
        }

        leaf craft-gui-admin-state {
          ui:ui-name "Craft GUI Administrative State";
          type cienawstypes:enabled-disabled-enum;
          description
            "Craft GUI administrative state.";
        }

        leaf inactivity-timeout {
          ui:ui-name "Inactivity Timeout";
          type uint16 {
            range "1..1500";
          }
          units "minutes";
          description
            "HTTPS inactivity timeout period, in minutes.";
        }

        container certificate-verification {
          ui:ui-name "Certification Verification";
          description
            "The HTTPS server configuration data for client certificate
             verification through mutual authentication and Online Certificate
             Status Protocol(OCSP).";
          leaf certificate-name {
            ui:ui-name "Certificate Name";
            type cienawstypes:string-maxl-32;
            description
              "The certificate name used by the HTTPS server.";
          }

          leaf trusted-dns {
            ui:ui-name "Trusted-DNS";
            type string {
              length "0..255";
            }
            description
              "Trusted DNS name used to check peer's certificate. The name
               should be fully qualified whenever possible, and can accept a
               leading period as wildcard.";
          }

          container mutual-authentication {
            ui:ui-name "Mutual Authentication";
            description
              "HTTPS server mutual authentication configuration data.";
            leaf admin-state {
              ui:ui-name "Admin State";
              type cienawstypes:enabled-disabled-enum;
              description
                "Whether apache HTTPS server mutual authentication verification
                 is enabled or disabled.";
            }
          }

          container ocsp {
            ui:ui-name "OCSP";
            description
              "HTTPS server configuration data for OCSP verification.";
            uses common-ocsp-group;
          }
        }
      }

      container grpc {
        ui:ui-name "gRPC Server";
        description
          "gRPC server configuration.";
        leaf admin-state {
          ui:ui-name "gRPC Server Admin State";
          type cienawstypes:enabled-disabled-enum;
          description
            "gRPC server administrative state.";
        }

        container certificate-verification {
          description
            "gRPC server configuration data for client certificate
             verification through mutual authentication.";
          leaf certificate-name {
            type string {
              length "0..32";
            }
            description
              "The certificate name used by the gRPC server.";
          }

          container mutual-authentication {
            description
              "gRPC server mutual authentication configuration data.";
            leaf admin-state {
              type cienawstypes:enabled-disabled-enum;
              description
                "Whether gRPC server mutual authentication verification
                 is enabled or disabled.";
            }
          }
        }
      }

      container netconf {
        ui:ui-name "Netconf Server";
        description
          "NETCONF server configuration.";
        leaf admin-state {
          ui:ui-name "Netconf Server State";
          type cienawstypes:enabled-disabled-enum;
          description
            "Indicate whether NETCONF server is enabled.";
        }

        leaf candidate-advertisement {
          ui:ui-name "Netconf Candidate Advertisement";
          type cienawstypes:enabled-disabled-enum;
          description
            "Whether NETCONF candidate advertisement is enabled or disabled.";
        }
      }

      container ssh {
        ui:ui-name "SSH Server";
        description
          "SSH server configuration.";
        leaf admin-state {
          ui:ui-name "SSH Server Admin State";
          type cienawstypes:enabled-disabled-enum;
          config false;
          description
            "SSH server administrative state. Currently a read-only attribute.
             SSH server is enabled by default and cannot be explicitly disabled.";
        }

        leaf operational-state {
          ui:ui-name "SSH Server Operational State";
          type cienawstypes:up-down-enum;
          config false;
          description
            "SSH server operational state.";
        }

        leaf authentication-retries {
          ui:ui-name "SSH Auth Retries";
          type uint8 {
            range "1..3";
          }
          description
            "Number of authentication retries allowed before the SSH connection
             is dropped.";
        }

        leaf listener-port {
          ui:ui-name "SSH Listener Port";
          type uint16 {
            range "22..65535";
          }
          description
            "Configured SSH listener port. Default is port 22.";
        }

        leaf session-limit {
          ui:ui-name "SSH Session Limit";
          type uint16;
          config false;
          description
            "SSH session limit. Read-only attribute.";
        }

        list allowed-clients {
          ui:ui-name "Allowed Client List";
          key "ip-address";
          max-elements 100;
          description
            "List of allowed client IP addresses.";
          leaf ip-address {
            ui:ui-name "IP Address";
            type cienawstypes:string-maxl-64;
            description
              "IP address for allowed SSH clients. When the list is not empty,
               only the clients in the list can login to the SSH server.";
          }
        }

        container algorithms {
          ui:ui-name "SSH Algorithms";
          description
            "Waveserver SSH algorithm lists.";
          list key-exchange {
            ui:ui-name "Key Exchange Algorithm List";
            ncx:user-write "update";
            key "algorithm-name";
            description
              "List of SSH key exchange algorithms.
               The algorithm names are system assigned.";
            leaf algorithm-name {
              ui:ui-name "Algorithm Name";
              type cienawstypes:string-maxl-64;
              description
                "The SSH key exchange algorithm name.";
            }

            leaf admin-state {
              ui:ui-name "Admin State";
              type cienawstypes:enabled-disabled-enum;
              description
                "SSH key exchange algorithm administrative state.";
            }
          }

          list encryption {
            ui:ui-name "Encryption Algorithm List";
            ncx:user-write "update";
            key "algorithm-name";
            description
              "List of SSH encryption algorithms.
               The algorithm names are system assigned.";
            leaf algorithm-name {
              ui:ui-name "Algorithm Name";
              type cienawstypes:string-maxl-64;
              description
                "The SSH encryption algorithm name.";
            }

            leaf admin-state {
              ui:ui-name "Admin State";
              type cienawstypes:enabled-disabled-enum;
              description
                "SSH encryption algorithm administrative state.";
            }
          }

          list message-authentication-code {
            ui:ui-name "Message Authentication Code Algorithm List";
            ncx:user-write "update";
            key "algorithm-name";
            description
              "List of SSH message authentication code algorithms.
               The algorithm names are system assigned.";
            leaf algorithm-name {
              ui:ui-name "Algorithm Name";
              type cienawstypes:string-maxl-64;
              description
                "The SSH message authentication code algorithm name.";
            }

            leaf admin-state {
              ui:ui-name "Admin State";
              type cienawstypes:enabled-disabled-enum;
              description
                "SSH message authentication code algorithm administrative state.";
            }
          }

          list public-key-authentication {
            ui:ui-name "Public Key Authentication Algorithm List";
            ncx:user-write "update";
            key "algorithm-name";
            description
              "List of SSH public key authentication algorithms.
               The algorithm names are system assigned.";
            leaf algorithm-name {
              ui:ui-name "Algorithm Name";
              type cienawstypes:string-maxl-64;
              description
                "The SSH public key authentication algorithm name.";
            }

            leaf admin-state {
              ui:ui-name "Admin State";
              type cienawstypes:enabled-disabled-enum;
              description
                "SSH public key authentication algorithm administrative state.";
            }
          }
        }

        container key {
          ui:ui-name "SSH Key";
          config false;
          description
            "SSH key configuration status data. SSH keys serve as a means of
             identifying user to an SSH server using public-key cryptography
             and challenge-response authentication.";
          leaf type {
            ui:ui-name "SSH Key Type";
            type ssh-key-type-enum;
            description
              "SSH configured key type.";
          }

          leaf status {
            ui:ui-name "SSH Key Generation Status.";
            type ssh-key-generation-status-enum;
            description
              "SSH key generation status.";
          }

          container fingerprint {
            ui:ui-name "SSH Key Fingerprint";
            description
              "SSH key fingerprint data.";
            leaf type {
              ui:ui-name "SSH Key Fingerprint Type";
              type cienawstypes:string-maxl-16;
              description
                "SSH key fingerpint type.";
            }

            leaf value {
              ui:ui-name "SSH Key Fingerprint Value";
              type cienawstypes:string-maxl-64;
              description
                "SSH key fingerprint value.";
            }
          }

          list public-key-authentication-users {
            ui:ui-name "Public Key Authentication User List";
            key "user-name";
            description
              "List of users that use SSH public key authentication.";
            leaf user-name {
              ui:ui-name "User Name";
              type cienawstypes:string-maxl-64;
              description
                "The user name who uses SSH public key authentication.";
            }

            leaf key-type {
              ui:ui-name "Key Type";
              type ssh-key-type-enum;
              description
                "SSH configured key type.";
            }

            leaf key-status {
              ui:ui-name "Key Status";
              type ssh-public-key-user-status-enum;
              description
                "SSH public key status for the user.";
            }

            leaf user-key-error-status {
              ui:ui-name "User Key Error Status";
              type ssh-public-key-user-account-error-status-enum;
              description
                "SSH public key error status for the user.";
            }
          }
        }

        container client-key {
          ui:ui-name "SSH Client Key";
          config false;
          description
            "SSH client key configuration and data. SSH client key serves as a means of
             authentication to a remote SSH server using public-key cryptography.";
          leaf type {
            ui:ui-name "SSH Client Key Type";
            type ssh-client-key-type-enum;
            description
              "SSH client key type.";
          }

          leaf status {
            ui:ui-name "SSH Client Key Status.";
            type ssh-client-key-status-enum;
            description
              "SSH client key status.";
          }

          leaf public-key {
            ui:ui-name "SSH Client Public Key";
            type string {
              length "0..4096";
            }
            description
              "SSH client public-key.";
          }
        }
      }
    }

    container client-config {
      ui:ui-name "Client Configuration";
      description
        "Waveserver client configuration attributes.";
      container dhcp {
        ui:ui-name "DHCP Client Configuration";
        description
          "Waveserver DHCP client configuration attributes.";
        leaf admin-state {
          ui:ui-name "DHCP Client Admin State";
          type cienawstypes:enabled-disabled-enum;
          description
            "DHCP client administrative atate";
        }

        leaf operational-state {
          ui:ui-name "DHCP Client Operational State";
          type cienawstypes:up-down-enum;
          config false;
          description
            "DHCP client operational state.";
        }

        leaf interface-type {
          ui:ui-name "DHCP Client Interface Type";
          type enumeration {
            enum "remote" {
              value 0;
              description
                "Remote.";
            }
            enum "active" {
              value 1;
              description
                "Active.";
            }
          }
          description
            "DHCP client interface type.";
        }

        leaf dhcp-state {
          ui:ui-name "DHCP State";
          type dhcp-state-enum;
          config false;
          description
            "DHCP state.";
        }

        leaf discovery-interval {
          ui:ui-name "DHCP Client Discovery Interval";
          type uint32 {
            range "1..60";
          }
          units "seconds";
          description
            "DHCP client discovery interval in seconds.";
        }

        leaf requested-lease-time {
          ui:ui-name "DHCP Client Requested Lease Time";
          type uint32 {
            range "45..max";
          }
          units "seconds";
          description
            "DHCP client requested lease time in seconds.";
        }

        leaf lease-time {
          ui:ui-name "DHCP Client Lease Time";
          type uint32;
          units "seconds";
          config false;
          description
            "DHCP client lease time in seconds";
        }

        leaf lease-remaining {
          ui:ui-name "DHCP Client Lease Remaining";
          type uint32;
          units "seconds";
          config false;
          description
            "DHCP client lease time remaning in seconds.";
        }

        leaf renewal-time {
          ui:ui-name "DHCP Client Renewal Time";
          type uint32;
          units "seconds";
          config false;
          description
            "DHCP client renewal time (T1) in seconds.";
        }

        leaf renewal-remaining {
          ui:ui-name "DHCP Client Renewal Remaining";
          type uint32;
          units "seconds";
          config false;
          description
            "DHCP client remaining renewal time (T1) in seconds.";
        }

        leaf rebinding-time {
          ui:ui-name "DHCP Client Rebinding Time";
          type uint32;
          units "seconds";
          config false;
          description
            "DHCP client rebinding time (T2) in seconds.";
        }

        leaf rebinding-remaining {
          ui:ui-name "DHCP Client Rebinding Remaining";
          type uint32;
          units "seconds";
          config false;
          description
            "DHCP client remaining rebinding time (T2) in seconds.";
        }

        leaf dhcp-server {
          ui:ui-name "DHCP Server Ip Address";
          type cienawstypes:ipv4-address;
          config false;
          description
            "DHCP server ipv4 address.";
        }

        container options {
          ui:ui-name "DHCP Client Options";
          description
            "DHCP Options. A list of the enabled/requested options configured on the DHCP client.";
          reference
            "RFC-2132 - DHCP Options and BOOTP Vendor Extensions";
          leaf subnet-mask {
            ui:ui-name "DHCP Client Option Subnet Mask";
            type boolean;
            description
              "DHCP Option 1 - Subnet Mask.";
          }

          leaf time-offset {
            ui:ui-name "DHCP Client Option Time Offset";
            type boolean;
            description
              "DHCP Option 2 - Time Offset.";
          }

          leaf router {
            ui:ui-name "DHCP Client Option Router";
            type boolean;
            description
              "DHCP Option 3 - Router.";
          }

          leaf domain-server {
            ui:ui-name "DHCP Client Option Domain Server";
            type boolean;
            description
              "DHCP Option 6 - Domain Name Server.";
          }

          leaf log-server {
            ui:ui-name "DHCP Client Option Log Server";
            type boolean;
            description
              "DHCP Option 7 - Log Server.";
          }

          leaf host-name {
            ui:ui-name "DHCP Client Option Host Name";
            type boolean;
            description
              "DHCP Option 12 - Host Name.";
          }

          leaf domain-name {
            ui:ui-name "DHCP Client Domain Name";
            type boolean;
            description
              "DHCP Option 15 - Domain Name.";
          }

          leaf ntp-servers {
            ui:ui-name "DHCP Client Option NTP Servers";
            type boolean;
            description
              "DHCP Option 42 - Network Time Protocol Servers.";
          }

          leaf lease-time {
            ui:ui-name "DHCP Client Option Lease Time";
            type boolean;
            description
              "DHCP Option 51 - Lease Time.";
          }

          leaf tftp-server-name {
            ui:ui-name "DHCP Client Option TFTP Server Name";
            type boolean;
            description
              "DHCP Option 66 - TFTP Server Name.";
          }

          leaf bootfile-name {
            ui:ui-name "DHCP Client Option Bootfile Name";
            type boolean;
            description
              "DHCP Option 67 - Bootfile Name.";
          }
        }

        container options-data {
          ui:ui-name "DHCP Client Options Data";
          config false;
          description
            "Additional DHCP options data returned from the server.";
          reference
            "RFC-2132 - DHCP Options and BOOTP Vendor Extensions";
          leaf subnet-mask {
            ui:ui-name "DHCP Client Option Subnet Mask";
            type cienawstypes:ipv4-address;
            description
              "DHCP Option 1 - Subnet Mask.";
          }

          leaf time-offset {
            ui:ui-name "DHCP Client Option Time Offset";
            type int32;
            units "seconds";
            description
              "DHCP Option 2 - Time Offset from UTC, in seconds. A positive
               value indicates a location east of the zero meridian, and a
               negative value indicates a location west of the zero meridian.";
          }

          leaf-list router {
            ui:ui-name "DHCP Client Option Routers";
            type cienawstypes:ipv4-address;
            description
              "DHCP Option 3 - Router List.";
          }

          leaf-list domain-server {
            ui:ui-name "DHCP Client Option Domain Servers";
            type cienawstypes:ipv4-address;
            description
              "DHCP Option 6 - Domain Name Server List.";
          }

          leaf-list log-server {
            ui:ui-name "DHCP Client Option Log Servers";
            type cienawstypes:ipv4-address;
            description
              "DHCP Option 7 - Log Server List.";
          }

          leaf host-name {
            ui:ui-name "DHCP Client Option Host Name";
            type string;
            description
              "DHCP Option 12 - Host Name.";
          }

          leaf domain-name {
            ui:ui-name "DHCP Client Domain Name";
            type string;
            description
              "DHCP Option 15 - Domain Name.";
          }

          leaf-list ntp-servers {
            ui:ui-name "DHCP Client Option NTP Servers";
            type cienawstypes:ipv4-address;
            description
              "DHCP Option 42 - Network Time Protocol Server List.";
          }

          leaf lease-time {
            ui:ui-name "DHCP Client Option Lease Time";
            type uint32;
            units "seconds";
            description
              "DHCP Option 51 - Lease Time.";
          }

          leaf tftp-server-name {
            ui:ui-name "DHCP Client Option TFTP Server Name";
            type string;
            description
              "DHCP Option 66 - TFTP Server Name.";
          }

          leaf bootfile-name {
            ui:ui-name "DHCP Client Option Bootfile Name";
            type string;
            description
              "DHCP Option 67 - Bootfile Name.";
          }
        }
      }

      container dhcpv6 {
        ui:ui-name "DHCPv6 Client Configuration";
        description
          "Waveserver DHCPv6 client configuration attributes.";
        leaf admin-state {
          ui:ui-name "DHCPv6 Client Admin State";
          type cienawstypes:enabled-disabled-enum;
          description
            "DHCPv6 client administrative atate";
        }

        leaf operational-state {
          ui:ui-name "DHCPv6 Client Operational State";
          type cienawstypes:up-down-enum;
          config false;
          description
            "DHCPv6 client operational state.";
        }

        leaf dhcp-state {
          ui:ui-name "DHCPv6 State";
          type dhcpv6-state-enum;
          config false;
          description
            "DHCPv6 state.";
        }

        leaf lease-time {
          ui:ui-name "DHCPv6 Client Lease Time";
          type uint32;
          units "seconds";
          config false;
          description
            "DHCPv6 client lease time in seconds";
        }

        leaf lease-remaining {
          ui:ui-name "DHCPv6 Client Lease Remaining";
          type uint32;
          units "seconds";
          config false;
          description
            "DHCPv6 client lease time remaning in seconds.";
        }

        leaf renewal-time {
          ui:ui-name "DHCPv6 Client Renewal Time";
          type uint32;
          units "seconds";
          config false;
          description
            "DHCPv6 client renewal time (T1) in seconds.";
        }

        leaf renewal-remaining {
          ui:ui-name "DHCPv6 Client Renewal Remaining";
          type uint32;
          units "seconds";
          config false;
          description
            "DHCPv6 client remaining renewal time (T1) in seconds.";
        }

        leaf rebinding-time {
          ui:ui-name "DHCPv6 Client Rebinding Time";
          type uint32;
          units "seconds";
          config false;
          description
            "DHCPv6 client rebinding time (T2) in seconds.";
        }

        leaf rebinding-remaining {
          ui:ui-name "DHCPv6 Client Rebinding Remaining";
          type uint32;
          units "seconds";
          config false;
          description
            "DHCPv6 client remaining rebinding time (T2) in seconds.";
        }

        leaf dhcp-server-id {
          ui:ui-name "DHCPv6 Server DUID";
          type string;
          config false;
          description
            "DHCPv6 server DUID";
        }

        leaf dhcp-client-id {
          ui:ui-name "DHCPv6 Client DUID";
          type string;
          config false;
          description
            "DHCPv6 client DUID";
        }

        leaf dhcp-vendor-class-id {
          ui:ui-name "DHCPv6 Vendor class DUID";
          type string;
          config false;
          description
            "DHCPv6 vendor class DUID";
        }

        leaf dhcp-ip-address {
          ui:ui-name "DHCPv6 Server Ipv6 Address";
          type cienawstypes:ipv6-prefix;
          config false;
          description
            "DHCPv6 ipv6 address.";
        }

        container options-state {
          ui:ui-name "DHCPv6 Client Options";
          description
            "DHCPv6 Options. A list of the enabled/requested options configured on the DHCPv6 client.";
          reference
            "RFC-8415 - Dynamic Host Configuration Protocol for IPv6";
          leaf dns-servers {
            ui:ui-name "DHCPv6 Client Option DNS Servers";
            type boolean;
            description
              "DHCPv6 Option 23 - Domain Name System Servers.";
          }

          leaf ntp-server {
            ui:ui-name "DHCPv6 Client Option NTP Servers";
            type boolean;
            description
              "DHCPv6 Option 56 - Network Time Protocol Servers.";
          }

          leaf bootfile-url {
            ui:ui-name "DHCPv6 Client Option Bootfile URL";
            type boolean;
            description
              "DHCPv6 Option 59 - Bootfile URL.";
          }
        }

        container options-data {
          ui:ui-name "DHCPv6 Client Options Data";
          config false;
          description
            "Additional DHCPv6 options data returned from the server.";
          reference
            "RFC-8415 - Dynamic Host Configuration Protocol for IPv6";
          leaf-list dns-servers {
            ui:ui-name "DHCPv6 Client Option DNS Servers";
            type cienawstypes:ipv6-address;
            description
              "DHCPv6 Option 23 - Domain Name Servers.";
          }

          leaf-list ntp-server {
            ui:ui-name "DHCPv6 Client Option NTP Servers";
            type cienawstypes:ipv6-address;
            description
              "DHCPv6 Option 56 - Network Time Protocol Server.";
          }

          leaf bootfile-url {
            ui:ui-name "DHCPv6 Client Option Bootfile URL";
            type string;
            description
              "DHCPv6 Option 59 - Bootfile URL.";
          }
        }
      }

      container grpc {
        ui:ui-name "gRPC Client Configuration";
        description
          "Waveserver gRPC Client configuration attributes.";
        list server {
          ui:ui-name "Remote Server List";
          key "address";
          description
            "List of remote servers. Entries may be configured in this list to
             configure trusted-dns on a per-server basis, for example in certain
             dial-out telemetry operational workflows.";
          leaf address {
            ui:ui-name "Remote Server Address";
            type inet:host;
            mandatory true;
            description
              "Configured IP address or Domain Name of the remote server/collector.";
          }

          leaf trusted-dns {
            ui:ui-name "Trusted-DNS";
            type string {
              length "0..255";
            }
            mandatory true;
            description
              "Trusted DNS name used to check peer's certificate. The name
               should be a fully qualified domain name.";
          }
        }
      }

      container ntp {
        ui:ui-name "NTP Client Configuration";
        description
          "Waveserver NTP client configuration attributes.";
        leaf admin-state {
          ui:ui-name "NTP Client Admin State";
          type cienawstypes:enabled-disabled-enum;
          description
            "NTP client administrative state.";
        }

        leaf operational-state {
          ui:ui-name "NTP Client Operational State";
          type cienawstypes:up-down-enum;
          config false;
          description
            "NTP client operational state.";
        }

        leaf authentication-state {
          ui:ui-name "NTP Client Authentication State";
          type cienawstypes:enabled-disabled-enum;
          description
            "NTP client authentication state. When enabled, only MD5
             authenticated packets will be used to synchronize the time.";
        }

        leaf sha1key-authentication-state {
          ui:ui-name "NTP SHA1 Authentication State";
          type cienawstypes:enabled-disabled-enum;
          description
            "NTP SHA1 administrative state. When enabled, only SHA1
             authenticated packets will be used to synchronize the time.";
        }

        leaf autokey-authentication-state {
          ui:ui-name "NTP Autokey Authentication State";
          type cienawstypes:enabled-disabled-enum;
          description
            "NTP client autokey authentication state. A RSA host key and an X509
             certificate (RSA-SHA1) will be created (if not exist) and saved. The
             host key and certificate will be loaded to NTP daemon only if the
             NTP autokey is enabled on Waveserver";
        }

        leaf autokey-certificate-present {
          ui:ui-name "NTP Autokey Certificate Status";
          type boolean;
          config false;
          description
            "The status of the autokey authentication certificate, indicating
             whether the certificate is present.";
        }

        leaf autokey-type {
          ui:ui-name "NTP Autokey Type";
          type cienawstypes:string-maxl-64;
          config false;
          description
            "The NTP autokey type.";
        }

        leaf autokey-signature-algorithm {
          ui:ui-name "NTP Autokey Signature Algorithm";
          type cienawstypes:string-maxl-64;
          config false;
          description
            "Algorithm used by the CA to sign the NTP autokey certificate.";
        }

        leaf autokey-valid-from {
          ui:ui-name "NTP Autokey Valid From";
          type cienawstypes:string-maxl-64;
          config false;
          description
            "The date that the certificate is valid from and the passed validity time.";
        }

        leaf autokey-valid-to {
          ui:ui-name "NTP Autokey Valid To";
          type cienawstypes:string-maxl-64;
          config false;
          description
            "The date that the certificate is valid to and the remaining time.";
        }

        leaf mode {
          ui:ui-name "NTP Client Mode";
          type enumeration {
            enum "polling" {
              description
                "NTP client is in polling mode.";
            }
            enum "broadcast" {
              description
                "NTP client is in broadcast mode.";
            }
            enum "multicast" {
              description
                "NTP client is in multicast mode.";
            }
          }
          description
            "NTP client mode.";
        }

        leaf polling-interval {
          ui:ui-name "NTP Polling Interval";
          type uint32 {
            range "16|32|64|128|256|512|1024|2048|4096|8192|16384|32768|65536";
          }
          units "seconds";
          description
            "The NTP client polling interval, in seconds. Applicable only when
             NTP client mode is set to 'polling'. This is a global setting that
             applies to all configured NTP peer servers.";
        }

        leaf delay {
          type cienawstypes:decimal-3-dig;
          units "ms";
          config false;
          description
            "Round trip delay to the active NTP peer, in milliseconds.";
        }

        leaf offset {
          type cienawstypes:decimal-3-dig;
          units "ms";
          config false;
          description
            "The time offset between the NTP client and server, in milliseconds.";
        }

        leaf jitter {
          type cienawstypes:decimal-3-dig;
          units "ms";
          config false;
          description
            "The mean deviation/dispersion of multiple time samples from the
             active NTP peer, in milliseconds.";
        }

        leaf synchronized {
          type boolean;
          config false;
          description
            "Specifies whether NTP client has synchronized the system time
             with a remote peer server.";
        }

        list ntp-key {
          ui:ui-name "NTP Auth Keys";
          key "key-id";
          max-elements 32;
          description
            "List of NTP authentication keys.";
          leaf key-id {
            ui:ui-name "NTP Auth Key ID";
            type uint16;
            mandatory true;
            description
              "Unique index value for the NTP authentication key.";
          }

          leaf key-type {
            ui:ui-name "NTP Key Type";
            type enumeration {
              enum "MD5" {
                description
                  "Authentication key uses MD5 encryption.";
              }
              enum "SHA1" {
                description
                  "Authentication key uses SHA1 encryption.";
              }
            }
            description
              "Encryption type used for the NTP authentication key.";
          }

          leaf key-value {
            ui:ui-name "NTP Key Value";
            type string {
              length "2..40";
            }
            description
              "NTP authentication key value.";
          }
        }

        list server {
          ui:ui-name "NTP Server List";
          key "address";
          max-elements 10;
          description
            "List of NTP servers to use for time synchronization.";
          leaf address {
            ui:ui-name "NTP Server Address";
            type cienawstypes:ipaddr-or-hostname;
            mandatory true;
            description
              "Configured IP address or Domain Name of the remote NTP server.";
          }

          leaf ip-address {
            ui:ui-name "NTP Server IP";
            type cienawstypes:string-maxl-64;
            config false;
            description
              "Operational IP address associated with the remote NTP server,
               if configured/available, or 'Unresolved' otherwise.";
          }

          leaf autokey-authentication {
            ui:ui-name "Autokey Authentication";
            type cienawstypes:enabled-disabled-enum;
            description
              "Whether autokey authentication method is enabled for the server.
               The 'enabled' state will only be effective when the
               'ntp/authentication-state' is 'enabled'.";
          }

          leaf admin-state {
            ui:ui-name "NTP Server Admin State";
            type cienawstypes:enabled-disabled-enum;
            description
              "NTP remote server administrative state.";
          }

          leaf operational-state {
            ui:ui-name "NTP Server Operational State";
            type cienawstypes:up-down-enum;
            config false;
            description
              "NTP remote server operational state.";
          }

          leaf key-id {
            ui:ui-name "NTP Server Key ID";
            type leafref {
              path "../../ntp-key/key-id";
            }
            description
              "Leafref to 'ntp-key' list 'key-id' values.";
          }

          leaf reachable {
            ui:ui-name "NTP Server Reachable";
            type boolean;
            config false;
            description
              "Indicates whether the NTP remote server is reachable or not.";
          }

          leaf authenticated {
            ui:ui-name "NTP Server Authenticated";
            type boolean;
            config false;
            description
              "Indicates whether the last message received from the peer has
               been correctly authenticated. If authentication is not enabled,
               or the server is unreachable, this will be false.";
          }

          leaf server-condition {
            ui:ui-name "NTP Server Condition";
            type enumeration {
              enum "rejected" {
                value 0;
                description
                  "Peer rejected.";
              }
              enum "passed-sanity-checks" {
                value 1;
                description
                  "Peer passed sanity checks.";
              }
              enum "passed-correctness-checks" {
                value 2;
                description
                  "Peer passed correctness checks.";
              }
              enum "passed-candidate-checks" {
                value 3;
                description
                  "Peer passed candidate checks.";
              }
              enum "passed-outlyer-checks" {
                value 4;
                description
                  "Peer passed outlyer checks.";
              }
              enum "selected-distance-exceeded" {
                value 5;
                description
                  "Current selected synchronization source; max distance exceeded.";
              }
              enum "selected-distance-okay" {
                value 6;
                description
                  "Current selected synchronization source; max distance okay.";
              }
              enum "pps-peer" {
                value 7;
                description
                  "Current selected pulse-per-second (PPS) source.";
              }
              enum "reaching" {
                value 254;
                description
                  "Peer in reaching/syncing state.";
              }
              enum "error" {
                value 255;
                description
                  "An error occurred with this peer.";
              }
            }
            config false;
            description
              "NTP remote server peer selection condition.";
            reference
              "RFC 1305 - Network Time Protocol.";
          }

          leaf offset {
            ui:ui-name "NTP Server Offset";
            type cienawstypes:decimal-3-dig;
            units "ms";
            config false;
            description
              "Estimated current time offset between the NTP client and server,
               in milliseconds.";
          }
        }

        list multicast-server {
          ui:ui-name "NTP Multicast Server List";
          key "ip-address";
          max-elements 10;
          description
            "List of NTP multicast servers to use for time synchronization.";
          leaf ip-address {
            ui:ui-name "NTP Multicast Server IP";
            type cienawstypes:ipv6-address;
            description
              "Configured IPv6 address for NTP Multicast server.";
          }
        }
      }

      container dns {
        ui:ui-name "DNS Client Configuration";
        description
          "Waveserver DNS client configuration attributes.";
        leaf admin-state {
          ui:ui-name "DNS Client Admin State";
          type cienawstypes:enabled-disabled-enum;
          description
            "DNS client administrative state.";
        }

        leaf operational-state {
          ui:ui-name "DNS Client Operational State";
          type cienawstypes:up-down-enum;
          config false;
          description
            "DNS client operational state.";
        }

        list server {
          ui:ui-name "DNS Server List";
          key "ip-address";
          max-elements 5;
          description
            "List of DNS servers to use for domain name resolution. DNS servers
             can be manually created by the user, or dynamically created by via
             DHCP. Waveserver supports up to 3 manually provisioned DNS servers
             and up to 2 DHCP-assigned servers.";
          leaf ip-address {
            ui:ui-name "DNS Server IP";
            type cienawstypes:ip-address;
            description
              "IP address associated with the remote DNS server.";
          }

          leaf admin-state {
            ui:ui-name "DNS Server Admin State";
            type cienawstypes:enabled-disabled-enum;
            description
              "DNS remote server administrative state.";
          }

          leaf operational-state {
            ui:ui-name "DNS Server Operational State";
            type cienawstypes:up-down-enum;
            config false;
            description
              "DNS remote server operational state.";
          }

          leaf source {
            type enumeration {
              enum "user" {
                value 1;
                description
                  "The server was manually configured by the user.";
              }
              enum "dhcp" {
                value 2;
                description
                  "The server was automatically configured via DHCP.";
              }
              enum "both" {
                value 3;
                description
                  "The server was configured by both DHCP and user.";
              }
            }
            config false;
            description
              "Specifies whether the server configuration data was originated
               by the user, or auto-created via DHCP, or both.";
          }

          leaf user-priority {
            ui:ui-name "User Priority";
            type uint8 {
              range "1..3";
            }
            description
              "User-assigned DNS server priority. Only applicable when server
               source is 'user' or 'both'. Ignored otherwise.";
          }

          leaf dhcp-priority {
            ui:ui-name "dhcp Priority";
            type uint8;
            config false;
            description
              "DHCP-assigned DNS server priority. Only applicable when server
               source is 'dhcp' or 'both'. Empty/omitted otherwise.";
          }

          leaf operational-priority {
            ui:ui-name "Operational Priority";
            type uint8;
            config false;
            description
              "Actual operational priority value assigned by the system based
               on user/dhcp assigned values.";
          }
        }
      }
    }

    container xftp-config {
      ui:ui-name "XFTP Configuration";
      description
        "Waveserver system XFTP configuration attributes.";
      uses xftp-config-group;
    }

    container global-provisioning {
      ui:ui-name "Global Provisioning";
      description
        "Waveserver system global provisioning attributes.";
      leaf encryption-only {
        ui:ui-name "Encryption Only";
        type boolean;
        description
          "A boolean value indicating whether the current chassis configuration
           requires encryption modules only. If true, a user-initiated request
           to pre-create clear-text MOTR equipment will be rejected.";
      }

      container line-config {
        ui:ui-name "Line Config";
        description
          "Waveserver system line configuration.";
        leaf line-protection {
          ui:ui-name "Line Protection";
          type line-protection-enum;
          description
            "Line protection settings. If line protection is enabled, this
             means that the photonic line the Waveserver is connected to has
             protection enabled. In the event of a line side fault, the
             protection card on the line side will select the protection path
             and the modems will reacquire the signal on the alternate path.
             While the switch is occuring, link state messaging will be
             disabled to the clients so that the connected devices do not
             attempt a switch or a restoration.";
        }
      }
    }

    container lamp-test {
      ui:ui-name "Lamp Test";
      description
        "Waveserver lamp test attributes.";
      leaf admin-state {
        ui:ui-name "Admin State";
        type cienawstypes:enabled-disabled-enum;
        description
          "Enable or disable the system lamp test. The lamp-test admin-state
           will be automatically disabled once the timeout period has expired.";
      }

      leaf mode {
        ui:ui-name "Mode";
        type enumeration {
          enum "flash" {
            description
              "Lamp flash mode.";
          }
        }
        config false;
        description
          "Lamp mode selection. The default mode is flash. It is the only mode
           currently supported";
      }

      leaf target-type {
        ui:ui-name "Target Type";
        type enumeration {
          enum "chassis" {
            description
              "Chassis target type. This is the default target type. If
               specified, the target-id field will be reset/empty.";
          }
          enum "slot" {
            description
              "Slot target type. The slot number must also be specified in the
               target-id field.";
          }
          enum "port" {
            description
              "Port target type. The port-id(s) must also be specified in the
               target-id field.";
          }
        }
        description
          "Lamp testing target type. It can be chassis, slot, or port. The
           default type is chassis. When the target-type is slot or port, the
           slot/port identifier should also be set for the selected target(s)
           to be tested.";
      }

      leaf target-id {
        ui:ui-name "Target ID";
        type cienawstypes:string-maxl-128;
        description
          "Lamp testing target ID string. Must be specified when target-type is
           'slot' or 'port'. When the target-type is 'slot' the target-id should
           be a slot number (e.g. 1, 2, or 3). When the target-type is 'port'
           the target-id should be a port-id (e.g. '1-1') or comma-separated
           list of port-id's (e.g. '1-1,1-2,1-3').";
      }

      leaf timeout {
        ui:ui-name "Timeout";
        type uint32;
        units "seconds";
        description
          "The number of seconds the lamp flash testing will be operating when
           enabled.";
      }
    }

    container management {
      ui:ui-name "Management Configuration";
      description
        "Waveserver system management configuration attributes.";
      container caching {
        ui:ui-name "Caching";
        description
          "Run time cache setting for config operations on management interfaces.";
        leaf openconfig {
          ui:ui-name "OpenConfig";
          type cienawstypes:enabled-disabled-enum;
          description
            "OpenConfig cache config enable or disable.";
        }
      }

      container query-limits {
        ui:ui-name "Query Limits";
        description
          "Run time query limits for get operations on management interfaces.";
        container netconf {
          ui:ui-name "NETCONF";
          description
            "NETCONF protocol source type.";
          leaf pm-history-bins {
            ui:ui-name "PM History Bins";
            type uint8 {
              range "0..96";
            }
            description
              "Maximum query limit for PM history bins in NETCONF get responses.";
          }
        }

        container rest {
          ui:ui-name "REST";
          description
            "REST protocol source type.";
          leaf pm-history-bins {
            ui:ui-name "PM History Bins";
            type uint8 {
              range "0..96";
            }
            description
              "Maximum query limit for PM history bins in REST get responses.";
          }
        }

        container gnmi {
          ui:ui-name "gNMI";
          description
            "gNMI protocol source type.";
          leaf pm-history-bins {
            ui:ui-name "PM History Bins";
            type uint8 {
              range "0..96";
            }
            description
              "Maximum query limit for PM history bins in gNMI get responses.";
          }
        }
      }

      container root-scope {
        description
          "Control for root-level get and replace operations for management interfaces.";
        container netconf {
          description
            "NETCONF protocol source type.";
          leaf get {
            type root-scope-enum;
            description
              "Scope for NETCONF root-level get operations.";
          }

          leaf replace {
            type root-scope-enum;
            description
              "Scope for NETCONF root-level replace operations.";
          }
        }

        container rest {
          description
            "REST protocol source type.";
          leaf get {
            type root-scope-enum;
            description
              "Scope for REST root-level get operations.";
          }

          leaf replace {
            type root-scope-enum;
            description
              "Scope for REST root-level replace operations.";
          }
        }

        container gnmi {
          description
            "gNMI protocol source type.";
          leaf get {
            type root-scope-enum;
            description
              "Scope for gNMI root-level get operations.";
          }

          leaf replace {
            type root-scope-enum;
            description
              "Scope for gNMI root-level replace operations.";
          }
        }
      }
    }

    container environment {
      ui:ui-name "Linux Environment";
      description
        "Waveserver system linux environment attributes.";
      container root {
        ui:ui-name "Root User Configuration";
        description
          "Waveserver system user root configuration.";
        leaf password {
          ui:ui-name "Root Password";
          ncx:password;
          type cienawstypes:string-maxl-128;
          description
            "User root password string.";
        }

        leaf secret {
          ui:ui-name "Root Password Secret";
          type cienawstypes:string-maxl-256;
          description
            "The encrypted user password string, supplied as a hashed value.";
        }
      }

      container diag {
        ui:ui-name "Diag User Configuration";
        description
          "System level default environment configuration for diag level users.";
        leaf shell {
          ui:ui-name "Default Shell";
          type enumeration {
            enum "cli" {
              description
                "A Waveserver command-line interface session will be launched
                 upon diag level user login. This is the default system
                 behavior.";
            }
            enum "system" {
              description
                "A successful authentication of a diag level user account by
                 the SSH server via local or remote (Radius/TACACS) service
                 shall put the user in the system shell (e.g. Linux shell).";
            }
          }
          description
            "The default shell session type for authenticated diag users.";
        }

        leaf sudo {
          ui:ui-name "Sudo";
          type boolean;
          description
            "Specifies whether or not diag users will be automatically added to
             the sudoers list. Default is disabled.";
        }
      }

      container shell {
        ui:ui-name "System Shell Configuration";
        description
          "System level default environment configuration for diagnostic shell access.";
        leaf admin-state {
          type cienawstypes:enabled-disabled-enum;
          description
            "Diagnostic shell access control.
             Default value is enabled.
             Only super level user is allowed to change to disabled.
             Setting back to enabled state requires a reset-to-factory-defaults.
             When disabled, diag user cannot access the diagnostic shell.
             Root account is blocked from logging in to the console port.
             CLI commands to modify files on the filesystem are rejected.";
        }
      }
    }

    container auto-config-recovery {
      ui:ui-name "Auto Config Recovery";
      description
        "Waveserver system automatic configuration recovery for CP replacement attributes.";
      leaf config-mismatch-detection-state {
        ui:ui-name "Config Mismatch Detection State";
        type cienawstypes:enabled-disabled-enum;
        description
          "Indicate whether config mismatch detection for CP replacement is enabled.";
      }

      leaf admin-state {
        ui:ui-name "Auto Config Recovery state";
        type cienawstypes:enabled-disabled-enum;
        description
          "Indicate whether auto config recovery is enabled.";
      }

      leaf passphrase {
        ui:ui-name "Passphrase";
        type string {
          length "0|8..256";
        }
        description
          "Passphrase used for backup encryption (Default: none, use builtin key).";
      }

      leaf audit-interval {
        ui:ui-name "Audit Interval";
        type uint16 {
          range "0..28800";
        }
        description
          "Audit Interval in minutes.";
      }

      leaf operational-state {
        ui:ui-name "Operational State";
        type cienawstypes:enabled-disabled-enum;
        config false;
        description
          "Indicate whether operational state is enabled.";
      }

      leaf last-backup-reason {
        ui:ui-name "Last Backup Reason";
        type cienawstypes:string-maxl-32;
        config false;
        description
          "The last backup reason string.";
      }

      leaf time-of-last-backup {
        ui:ui-name "Time Of Last Backup";
        type cienawstypes:string-maxl-32;
        config false;
        description
          "The date and time of the last auto-config backup, in 'YYYY-MM-DDTHH:MM:SS[+|-]hh:mm'
           format, or omitted if not applicable or unavailable.

           The string format follows IETF yang date-and-time specifications, compliant
           with RFC-6991. The base date and time portion of the string represents
           Coordinated Universal Time (UTC), and a non-zero hh:mm offset suffix indicates the
           system-configured local timezone offset at the time the event was recorded, and not
           necessarily when it was retrieved.

           When system timezone is set to UTC or no time-offset value is provisioned,
           the '+00:00' suffix will be used to indicate UTC time with no local offset.";
        reference
          "RFC 3339: Date and Time on the Internet: Timestamps
           RFC 6991: Common Yang Data Types";
      }

      leaf time-of-last-audit {
        ui:ui-name "Time Of Last Audit";
        type cienawstypes:string-maxl-32;
        config false;
        description
          "The date and time of the last auto-config audit, in 'YYYY-MM-DDTHH:MM:SS[+|-]hh:mm'
           format, or omitted if not applicable or unavailable.

           The string format follows IETF yang date-and-time specifications, compliant
           with RFC-6991. The base date and time portion of the string represents
           Coordinated Universal Time (UTC), and a non-zero hh:mm offset suffix indicates the
           system-configured local timezone offset at the time the event was recorded, and not
           necessarily when it was retrieved.

           When system timezone is set to UTC or no time-offset value is provisioned,
           the '+00:00' suffix will be used to indicate UTC time with no local offset.";
        reference
          "RFC 3339: Date and Time on the Internet: Timestamps
           RFC 6991: Common Yang Data Types";
      }
    }

    container state-dump-status {
      ui:ui-name "State Dump Status";
      config false;
      description
        "Status information about an active or recently completed state-dump
         collection operation.";
      leaf running-status {
        type enumeration {
          enum "inactive" {
            description
              "Default value, state dump has not been run since system restart.";
          }
          enum "active" {
            description
              "State dump is currently running.";
          }
          enum "finished" {
            description
              "State dump finished and the tarball was generated.";
          }
          enum "error" {
            description
              "State dump finished but did not complete successfully.";
          }
        }
        description
          "The current status of the state dump.";
      }

      leaf last-run {
        type string;
        description
          "The date and time of the most recent state-dump collection.";
      }

      leaf location {
        type string;
        description
          "The local file path of the tarball from the most recent run.";
      }

      leaf error-string {
        type string;
        description
          "Error string returned from most recent state-dump activity.";
      }
    }

    container state-dump-config {
      ui:ui-name "State Dump Config";
      description
        "Configurable field about an active or recently completed state-dump
         collection operation.";
      leaf exclude-corefiles {
        type cienawstypes:enabled-disabled-enum;
        description
          "Indicates that exclude-corefiles is enabled or disabled.";
      }
    }

    container ssl {
      ui:ui-name "SSL";
      description
        "Waveserver SSL security configuration and operational data.";
      list tls-cipher-suite-algorithms {
        ui:ui-name "TLS Cipher Suite Algorithm List";
        ncx:user-write "update";
        key "algorithm-name";
        description
          "List of transport layer security(TLS) cipher suite algorithms.
           The algorithm names are system assigned.";
        leaf algorithm-name {
          ui:ui-name "Algorithm Name";
          type cienawstypes:string-maxl-64;
          description
            "The TLS cipher suite algorithm name.";
        }

        leaf admin-state {
          ui:ui-name "Admin State";
          type cienawstypes:enabled-disabled-enum;
          description
            "TLS cipher suite algorithm administrative state.";
        }
      }
    }

    container shell {
      ui:ui-name "Shell";
      description
        "Waveserver system CLI shell/session attributes.";
      leaf inactivity-timer {
        ui:ui-name "Inactivity Timer";
        type leafref {
          path "../../server-config/global-inactivity-timer";
        }
        status deprecated;
        description
          "Leafref to global session inactivity timer state.
           This attribute is deprecated. Has been moved to server-config container.";
      }

      leaf inactivity-timeout {
        ui:ui-name "Inactivity Timeout";
        type leafref {
          path "../../server-config/global-inactivity-timeout";
        }
        status deprecated;
        description
          "Leafref to global session inactivity timeout period, in minutes.
           This attribute is deprecated. Has been moved to server-config container.";
      }

      leaf more {
        ui:ui-name "Global More";
        type cienawstypes:enabled-disabled-enum;
        description
          "Global CLI/shell session pagination (more) behavior.";
      }

      leaf more-lines {
        ui:ui-name "More Lines";
        type uint16 {
          range "0..999";
        }
        description
          "Global CLI/shell session pagination (more) number of lines per page.";
      }

      leaf login-authentication-message {
        ui:ui-name "Login Authentication Message";
        type cienawstypes:enabled-disabled-enum;
        description
          "Toggles the authentication message for CLI/shell session logins.";
      }

      leaf login-banner-file {
        ui:ui-name "Login Banner File";
        type cienawstypes:string-maxl-254;
        description
          "Local file name containing the banner text to be displayed prior to
           CLI/shell session logins.";
      }

      leaf welcome-banner-file {
        ui:ui-name "Welcome Banner File";
        type cienawstypes:string-maxl-254;
        description
          "Local file name containing the welcome banner text to be displayed upon
           successful CLI/shell session logins.";
      }
    }

    container default-settings {
      ui:ui-name "System Default Settings";
      description
        "Waveserver system default configuration values.";
      container conditioning {
        description
          "Waveserver system default conditioning values. Ports are created with
           these values. When the system defaults are set, all existing ports
           have their values updated.";
        leaf type {
          type cienawstypes:conditioning-type;
          description
            "Egress UNI port consequent action for an EPL service to be applied
             on a far-end ingress UNI failure or network failure.";
        }

        leaf holdoff {
          type cienawstypes:conditioning-holdoff;
          description
            "Number of milliseconds the failure must be present before applying
             Egress UNI port consequent action for an EPL service.";
        }
      }

      leaf remote-management-auto-enable {
        type boolean;
        description
          "Enable GCC interfaces when module is created.";
      }

      leaf terrestrial-reach-limit {
        type int16 {
          range "0|250|500|1000|2000|2100|3000|4000|5000|8000";
        }
        units "km";
        description
          "The maximum reach allowed in km. The possible values are [250, 500, 1000, 2000,
           2100, 3000, 4000, 5000, 8000] for terrestrial modem class.
           [0] if the value is unknown/unavailable or inapplicable.";
      }
    }
  }

  container waveserver-system {
    ui:ui-name "System";
    description
      "Waveserver System configuration data and operational data.";
    uses waveserver-system-group;
  }

  rpc waveserver-system-state-dump {
    description
      "Dump system state information to a local or remote archive file. The RPC
       will return once the state dump collection has been initiated, rather than
       blocking until the operation is complete. User may retrieve on the status
       of an in-progress state-dump collection via the system state-dump container.";
    input {
      leaf file-name {
        ui:ui-name "File Name";
        type cienawstypes:string-maxl-254;
        description
          "The file name to store the system state data. If file-name is specified
           without server-to-use or url leafs then the state-dump file will be saved
           to the local file system.";
      }

      uses server-settings-group;

      leaf url {
        type string {
          length "0..512";
        }
        description
          "The URL specifying the remote location and package name to be uploaded.
           Example format is 'scp://<uid>:<pwd>@<ip-address>/<path>/<filename>'.
           If url leaf is specified and not empty, the xftp server-settings-group
           related leafs will be ignored.";
      }

      leaf exclude-corefiles {
        type boolean;
        description
          "Indicates if corefiles should be excluded.
              Defaults to false - i.e. corefiles will be included on omission.";
      }
    }

    output {
      leaf return-code {
        type uint32;
        description
          "return code: 0 is success; non-zero is failure";
      }

      leaf return-string {
        type cienawstypes:string-maxl-254;
        description
          "Return code description";
      }
    }
  }

  rpc waveserver-system-putfile {
    description
      "Transfer file to a specified destination.";
    input {
      leaf local-file-name {
        ui:ui-name "Local File Name";
        type cienawstypes:string-maxl-254;
        description
          "The local file name.";
      }

      leaf remote-file-name {
        ui:ui-name "Remote File Name";
        type cienawstypes:string-maxl-254;
        description
          "The remote file name.";
      }

      leaf remote-url {
        type string {
          length "0..512";
        }
        description
          "The URL specifying the remote location and file name to be transfered.
           Example format is 'scp://<uid>:<pwd>@<ip-address>/<path>/<filename>'.
           If url leaf is specified and not empty, the xftp server-settings-group
           related leafs will be ignored.";
      }

      uses server-settings-group;
    }

    output {
      leaf return-code {
        type uint32;
        description
          "return code: 0 is success; non-zero is failure";
      }

      leaf return-string {
        type cienawstypes:string-maxl-254;
        description
          "Return code description";
      }
    }
  }

  rpc waveserver-system-getfile {
    description
      "Get file from a specified source.";
    input {
      leaf local-file-name {
        ui:ui-name "Local File Name";
        type cienawstypes:string-maxl-254;
        description
          "The local file name.";
      }

      leaf remote-file-name {
        ui:ui-name "Remote File Name";
        type cienawstypes:string-maxl-254;
        description
          "The remote file name.";
      }

      leaf remote-url {
        type string {
          length "0..512";
        }
        description
          "The URL specifying the remote location and file name to be transfered.
           Example format is 'scp://<uid>:<pwd>@<ip-address>/<path>/<filename>'.
           If url leaf is specified and not empty, the xftp server-settings-group
           related leafs will be ignored.";
      }

      uses server-settings-group;
    }

    output {
      leaf return-code {
        type uint32;
        description
          "return code: 0 is success; non-zero is failure";
      }

      leaf return-string {
        type cienawstypes:string-maxl-254;
        description
          "Return code description";
      }
    }
  }

  rpc waveserver-system-set-date-time {
    description
      "An RPC to set system date and/or clock time.";
    input {
      leaf date {
        type string {
          length "1..11";
          pattern "\\d{4}-\\d{2}-\\d{2}|\\d{2}-\\d{2}-\\d{2}|\\d{2}-\\d{2}";
        }
        description
          "Date: must be in format: yyyy-mm-dd, or yy-mm-dd, or mm-dd.";
      }

      leaf time {
        type string {
          length "1..9";
          pattern "\\d{2}:\\d{2}:\\d{2}|\\d{2}:\\d{2}";
        }
        description
          "Time: must be in format: hh:mm:ss";
      }
    }

    output {
      leaf return-code {
        type uint32;
        description
          "return code: 0 is success; non-zero is failure";
      }

      leaf return-string {
        type string {
          length "0..254";
        }
        description
          "Return code description";
      }
    }
  }

  rpc waveserver-system-dns-resolve-ip {
    description
      "Use DNS protocol to resolve an IP address to an associated domain name,
       or resolve a host name to its associated IP address.";
    input {
      leaf address {
        type cienawstypes:ipaddr-or-hostname;
        mandatory true;
        description
          "IP address or Host Name to resolve.";
      }
    }

    output {
      leaf ip-address {
        type cienawstypes:string-maxl-64;
        description
          "The resolved IP address, if known, or 'Unknown' otherwise.";
      }

      leaf host-name {
        type cienawstypes:string-maxl-64;
        description
          "The resolved host name, if known, or 'Unknown' otherwise.";
      }

      leaf return-code {
        type uint32;
        description
          "return code: 0 is success; non-zero is failure";
      }

      leaf return-string {
        type cienawstypes:string-maxl-254;
        description
          "Return code description";
      }
    }
  }

  rpc waveserver-system-https-server-rsa-activate-p12-file {
    status obsolete;
    description
      "Activate a local p12-file to replace current https server certificate and private key.
       This RPC is now obsolete. Use waveserver-pkix-install-device-certificate instead.";
    input {
      leaf path {
        ui:ui-name "Path";
        type cienawstypes:string-maxl-254;
        mandatory true;
        description
          "The path and file name of a local p12-file downloaded from outside.";
      }

      leaf password {
        ui:ui-name "Password";
        type cienawstypes:string-maxl-128;
        description
          "The password for activation.";
      }
    }

    output {
      leaf return-code {
        type uint32;
        description
          "return code: 0 is success; non-zero is failure";
      }

      leaf return-string {
        type cienawstypes:string-maxl-254;
        description
          "Return code description";
      }
    }
  }

  rpc waveserver-system-tls-rsa-generate {
    description
      "Regenerate the system's default self-signed certificate.";

    output {
      leaf return-code {
        type uint32;
        description
          "return code: 0 is success; non-zero is failure";
      }

      leaf return-string {
        type cienawstypes:string-maxl-254;
        description
          "Return code description";
      }
    }
  }

  rpc waveserver-system-ssh-server-activate-host-key {
    description
      "Activate a SSH host key.";
    input {
      leaf host-key {
        ui:ui-name "Host Key";
        type string {
          length "1..64";
        }
        mandatory true;
        description
          "The SSH host key.";
      }

      leaf passphrase {
        ui:ui-name "Passphrase";
        type string {
          length "1..128";
        }
        mandatory true;
        description
          "The password for the SSH host key.";
      }
    }

    output {
      leaf return-code {
        type uint32;
        description
          "return code: 0 is success; non-zero is failure";
      }

      leaf return-string {
        type cienawstypes:string-maxl-254;
        description
          "Return code description";
      }
    }
  }

  rpc waveserver-system-ssh-server-delete-key {
    description
      "Delete the SSH key for the specified user.";
    input {
      leaf user {
        ui:ui-name "User";
        type string {
          length "1..32";
        }
        description
          "The user name for whom the key will be deleted.";
      }
    }

    output {
      leaf return-code {
        type uint32;
        description
          "return code: 0 is success; non-zero is failure";
      }

      leaf return-string {
        type cienawstypes:string-maxl-254;
        description
          "Return code description";
      }
    }
  }

  rpc waveserver-system-ssh-server-generate-key {
    description
      "Generate a SSH key.";
    input {
      leaf key-type {
        ui:ui-name "SSH Key Type";
        type ssh-key-type-enum;
        description
          "The SSH key type.";
      }

      leaf force {
        ui:ui-name "Force";
        type boolean;
        description
          "Whether to force the generation of the SSH key.";
      }

      uses server-settings-group;

      leaf url {
        type string {
          length "0..512";
        }
        description
          "The URL specifying the remote location and remote key file to be installed.
           Example format is 'scp://<uid>:<pwd>@<ip-address>/<path>/<filename>'.
           'server-to-use' setting is ignored when 'url' is specified.";
      }
    }

    output {
      leaf return-code {
        type uint32;
        description
          "return code: 0 is success; non-zero is failure";
      }

      leaf return-string {
        type cienawstypes:string-maxl-254;
        description
          "Return code description";
      }
    }
  }

  rpc waveserver-system-ssh-server-install-key {
    description
      "Install a SSH key for the specified user.";
    input {
      leaf user {
        ui:ui-name "User";
        type string {
          length "1..32";
        }
        description
          "The user name for whom the key will be generated.";
      }

      uses server-settings-group;

      leaf url {
        type string {
          length "0..512";
        }
        description
          "The URL specifying the remote location and remote key file to be installed.
           Example format is 'scp://<uid>:<pwd>@<ip-address>/<path>/<filename>'.
           'server-to-use' setting is ignored when 'url' is specified.";
      }
    }

    output {
      leaf return-code {
        type uint32;
        description
          "return code: 0 is success; non-zero is failure";
      }

      leaf return-string {
        type cienawstypes:string-maxl-254;
        description
          "Return code description";
      }
    }
  }

  rpc waveserver-system-ssh-client-generate-key {
    description
      "Generate a SSH client key of key-type.";
    input {
      leaf key-type {
        ui:ui-name "SSH Client Key Type";
        type ssh-client-key-type-enum;
        description
          "The SSH client key type.";
      }

      leaf force {
        ui:ui-name "Force";
        type boolean;
        description
          "Whether to force the generation of the SSH client key.";
      }
    }

    output {
      leaf return-code {
        type uint32;
        description
          "return code: 0 is success; non-zero is failure";
      }

      leaf return-string {
        type string {
          length "0..254";
        }
        description
          "Return code description";
      }
    }
  }

  rpc waveserver-system-ssh-client-transfer-public-key {
    description
      "Transfer SSH client public key to url location.";
    input {
      leaf ssh-copy-id {
        ui:ui-name "ssh-copy-id";
        type boolean;
        description
          "Use ssh-copy-id utility to copy and install public key to remote if it is true.";
      }

      leaf url {
        type string {
          length "0..512";
        }
        description
          "The URL specifying the remote location and file name to be transferred.
           If ssh-copy-id is true, no need to specify path and file name in url,
           an example is 'scp://<uid>:<pwd>@<ip-address>'.
           If ssh-copy-id is false, need path and file name in url,
           an example is 'scp://<uid>:<pwd>@<ip-address>/<path>/<filename>'.";
      }
    }

    output {
      leaf return-code {
        type uint32;
        description
          "return code: 0 is success; non-zero is failure";
      }

      leaf return-string {
        type string {
          length "0..254";
        }
        description
          "Return code description";
      }
    }
  }

  rpc waveserver-system-ssh-client-delete-key {
    description
      "Delete SSH client key.";

    output {
      leaf return-code {
        type uint32;
        description
          "return code: 0 is success; non-zero is failure";
      }

      leaf return-string {
        type string {
          length "0..254";
        }
        description
          "Return code description";
      }
    }
  }

  rpc waveserver-system-ntp-generate-autokey {
    description
      "Generate the autokey. The certificate created using ntp-keygen tool is
       valid for one year and should be updated periodically.";

    output {
      leaf return-code {
        type uint32;
        description
          "return code: 0 is success; non-zero is failure";
      }

      leaf return-string {
        type cienawstypes:string-maxl-254;
        description
          "Return code description";
      }
    }
  }

  rpc waveserver-system-ntp-sha1auth-import {
    description
      "Import NTP SHA1 keys from a file.";
    input {
      leaf filename {
        type string;
        mandatory true;
        description
          "NTP SHA1 authentication key filename.";
      }
    }

    output {
      leaf return-code {
        type uint32;
        description
          "Return code: 0 is success; non-zero is failure.";
      }

      leaf return-string {
        type cienawstypes:string-maxl-254;
        description
          "Return code description.";
      }
    }
  }

  rpc waveserver-system-client-config-dhcp-lease-renew {
    description
      "Renew DHCP client lease time.";

    output {
      leaf return-code {
        type uint32;
        description
          "return code: 0 is success; non-zero is failure";
      }

      leaf return-string {
        type cienawstypes:string-maxl-254;
        description
          "Return code description";
      }
    }
  }

  rpc waveserver-system-client-config-dhcpv6-lease-renew {
    description
      "Renew DHCPv6 client lease time.";

    output {
      leaf return-code {
        type uint32;
        description
          "return code: 0 is success; non-zero is failure";
      }

      leaf return-string {
        type cienawstypes:string-maxl-254;
        description
          "Return code description";
      }
    }
  }

  rpc waveserver-system-client-config-ntp-md5auth-import {
    description
      "To import NTP MD5 keys from a file.";
    input {
      leaf filename {
        ui:ui-name "File name";
        type cienawstypes:string-maxl-254;
        mandatory true;
        description
          "NTP MD5 authentication key filename.";
      }
    }

    output {
      leaf return-code {
        type uint32;
        description
          "return code: 0 is success; non-zero is failure";
      }

      leaf return-string {
        type cienawstypes:string-maxl-254;
        description
          "Return code description";
      }
    }
  }

  rpc waveserver-system-override-config-mismatch {
    description
      "To override the config mismatch status for CP replacement.";

    output {
      leaf return-code {
        type uint32;
        description
          "return code: 0 is success; non-zero is failure";
      }

      leaf return-string {
        type cienawstypes:string-maxl-254;
        description
          "Return code description";
      }
    }
  }

  rpc waveserver-system-auto-config-force-backup {
    description
      "Force a backup of the CP software load and configuration data to the AP for auto-recovery.";

    output {
      leaf return-code {
        type uint32;
        description
          "return code: 0 is success; non-zero is failure";
      }

      leaf return-string {
        type cienawstypes:string-maxl-254;
        description
          "Return code description";
      }
    }
  }
}
