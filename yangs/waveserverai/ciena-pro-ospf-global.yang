submodule ciena-pro-ospf-global {
  belongs-to ciena-pro-ospf {
    prefix pro-ospf;
  }

  import ietf-yang-types {
    prefix yang;
  }

  import ciena-pro-ospf-types {
    prefix pro-ospft;
  }

  import ciena-common-version {
    prefix ciena-common-version;
  }

  include "ciena-pro-ospf-common";

  description
    "This submodule provides OSPF configuration and operational
     state parameters that are global to a particular OSPF instance";

  revision 2019-10-08 {
    ciena-common-version:string "1.0.0";
    description
      "Initial revision";
  }

  grouping ospf-global-config {
    description
      "Global configuration for OSPF";
    leaf router-id {
      type yang:dotted-quad;
      description
        "A 32-bit number represented as a dotted quad assigned to
         each router running the OSPF protocol. This number should
         be unique within the autonomous system";
      reference
        "rfc2828";
    }

    leaf log-adjacency-changes {
      type boolean;
      description
        "When this leaf is set to true, a log message will be
         generated when the state of an OSPF neighbour changes.";
    }

    leaf hide-transit-only-networks {
      type boolean;
      description
        "When this leaf is set to true, do not advertise prefixes
         into OSPF that correspond to transit interfaces, as per
         the behaviour discussed in RFC6860.";
      reference
        "RFC6860 - Hiding Transit-Only Networks in OSPF";
    }

    leaf abr-capability {
      type identityref {
        base pro-ospft:OSPF-ABR-TYPE;
      }
      default "pro-ospft:RFC3509-COMPATIBLE";
      description
        "When the leaf is set to RFC2328-COMPATIBLE, the router
         acts as an ABR when it participates in multiple OSPF
         areas. It does not matter whether the backbone area
         exists or not. When the leaf is set to RFC3509-COMPATIBLE,
         the router acts as an ABR when the router participates
         in multiple OSPF areas, one of which must be backbone.";
    }
  }

  grouping ospf-global-spf-timers-config {
    description
      "Configuration parameters relating to global SPF timer
       parameters for OSPF";
    leaf initial-delay {
      type uint32;
      units "msec";
      description
        "The value of this leaf specifies the time between a change
         in topology being detected and the first run of the SPF
         algorithm.";
    }

    leaf maximum-delay {
      type uint32;
      units "msec";
      description
        "The value of this leaf specifies the maximum delay between
         a topology change being detected and the SPF algorithm
         running. This value is used for implementations that support
         increasing the wait time between SPF runs.";
    }
  }

  grouping ospf-global-lsa-generation-timers-config {
    description
      "Configuration parameters relating to global LSA generation
       parameters for OSPF";
    leaf initial-delay {
      type uint32;
      units "msec";
      description
        "The value of this leaf specifies the time between the first
         time an LSA is generated and advertised and the subsequent
         generation of that LSA.";
    }

    leaf maximum-delay {
      type uint32;
      units "msec";
      description
        "The value of this leaf specifies the maximum time between the
         generation of an LSA and the subsequent re-generation of that
         LSA. This value is used in implementations that support
         increasing delay between generation of an LSA";
    }
  }

  grouping ospf-global-spf-timers-state {
    description
      "Operational state parameters relating to OSPF global
       timers";
    uses ospf-common-timers;
  }

  grouping ospf-global-lsa-generation-timers-state {
    description
      "Operational state parameters relating to OSPF global
       timers";
    uses ospf-common-timers;
  }

  grouping ospf-global-graceful-restart-config {
    description
      "Configuration parameters relating to graceful restart for
       OSPF";
    leaf enabled {
      type boolean;
      description
        "When the value of this leaf is set to true, graceful restart
         is enabled on the local system. In this case, the system will
         use Grace-LSAs to signal that it is restarting to its
         neighbors.";
    }

    leaf helper-only {
      type boolean;
      description
        "Operate graceful-restart only in helper mode. When this leaf
         is set to true, the local system does not use Grace-LSAs to
         indicate that it is restarting, but will accept Grace-LSAs
         from remote systems, and suppress withdrawl of adjacencies
         of the system for the grace period specified";
    }
  }

  grouping ospf-global-max-metric-config {
    description
      "Configuration paramters relating to setting the OSPF
       maximum metric.";
    leaf set {
      type boolean;
      description
        "When this leaf is set to true, all non-stub interfaces of
         the local system are advertised with the maximum metric,
         such that the router does not act as a transit system,
         (similarly to the IS-IS overload functionality).";
      reference
        "RFC3137 - OSPF Stub Router Advertisement";
    }

    leaf timeout {
      type uint64;
      units "seconds";
      description
        "The delay, in seconds, after which the advertisement of
         entities with the maximum metric should be cleared, and
         the system reverts to the default, or configured, metrics.";
    }

    leaf-list include {
      type identityref {
        base pro-ospft:MAX_METRIC_INCLUDE;
      }
      description
        "By default, the maximum metric is advertised for all
         non-stub interfaces of a device. When identities are
         specified within this leaf-list, additional entities
         are also advertised with the maximum metric according
         to the values within the list.";
    }

    leaf-list trigger {
      type identityref {
        base pro-ospft:MAX_METRIC_TRIGGER;
      }
      description
        "By default, the maximum metric is only advertised
         when the max-metric/set leaf is specified as true.
         In the case that identities are specified within this
         list, they provide additional triggers (e.g., system
         boot) that may cause the max-metric to be set. In this
         case, the system should still honour the timeout specified
         by the max-metric/timeout leaf, and clear the max-metric
         advertisements after the expiration of this timer.";
    }
  }

  grouping ospf-global-structural-config {
    description
      "Top level structural grouping for OSPF global parameters";
    container global {
      description
        "Configuration and operational state parameters for settings
         that are global to the OSPF instance";
      uses ospf-global-config;

      container spf {
        description
          "Configuration and operational state parameters relating
           to timers governing the operation of SPF runs";
        uses ospf-global-spf-timers-config;
      }

      container max-metric {
        description
          "Configuration and operational state parameters relating
           to setting the OSPF maximum metric.";
        uses ospf-global-max-metric-config;
      }

      container lsa-generation {
        description
          "Configuration and operational state parameters relating
           to timers governing the generation of LSAs by the local
           system";
        uses ospf-global-lsa-generation-timers-config;
      }

      container graceful-restart {
        description
          "Configuration and operational state parameters for OSPF
           graceful restart";
        uses ospf-global-graceful-restart-config;
      }
    }
  }

  grouping ospf-global-structural-state {
    container timers {
      description
        "Configuration and operational state parameters for OSPF
         timers";
      container spf {
        description
          "Configuration and operational state parameters relating
           to timers governing the operation of SPF runs";
        uses ospf-global-spf-timers-state;
      }

      container lsa-generation {
        description
          "Configuration and operational state parameters relating
           to timers governing the generation of LSAs by the local
           system";
        uses ospf-global-lsa-generation-timers-state;
      }
    }
  }
}
