module ciena-waveserver-ptp-modem {
  namespace "urn:ciena:params:xml:ns:yang:ciena-ws:ciena-waveserver-ptp-modem";
  prefix ptp-modem;

  import ciena-waveserver-typedefs {
    prefix cienawstypes;
  }

  import ciena-waveserver-ptp {
    prefix ptp;
  }

  import ciena-waveserver-xcvr {
    prefix xcvr;
  }

  import ciena-ddf {
    prefix ddf;
  }

  import ciena-ui {
    prefix ui;
  }

  organization
    "Ciena Corporation";
  contact
    "Web URL: http://www.ciena.com/
     Postal:  7035 Ridge Road
             Hanover, Maryland 21076
             U.S.A.
     Phone:   +1 800-921-1144
     Fax:     +1 410-694-5750";
  description
    "This module defines modem-transceiver PTP data for the Waveserver. It
     augments the ciena-waveserver-ptp module. The PTP model represents the
     signal carried by the modem transceiver at a physical line port. The PTP
     objects are automatically provisioned during service module installation.";

  revision 2023-08-10 {
    description
      "Added 'adaptive' mode to 'tx-dispersion-compensation-mode' leaf.
       Updated 'expected-restoration-time' range to 0-1800.
       Added 'actual-tx-path-dispersion-value' leaf in 'modem' container.";
    reference
      "Waveserver OS R2.5 user's guide.";
  }
  revision 2022-10-05 {
    description
      "Added 'line-fail' to 'modem' container.";
    reference
      "Waveserver OS R2.4 user's guide.";
  }
  revision 2021-09-28 {
    description
      "Added 'regen-mate' to 'modem' container.";
    reference
      "Waveserver OS R2.3.1 user's guide.";
  }
  revision 2021-05-14 {
    description
      "Removed 'pre-fec-bit-error-rate', 'q-factor', 'pdl', 'esnr', 'snr-external', and
       'cycle-slip-indicator' from modem container. Moved to waveserver-statistics augmentation.
       Removed unsupported/deprecated 'allocated-spectral-width' leaf.
       Updated description for 'actual-reach' leaf.
       Updated 'when' statements for WL5n/400-ZR/QSFP-DD PTPs and added 'is-coherent' conditional.
       Added 'channel-contention-threshold' leaf.";
    reference
      "Waveserver OS R2.1 user's guide.";
  }
  revision 2020-10-19 {
    description
      "Added leaves 'pre-fec-bit-error-rate', 'q-factor', 'pdl', 'esnr', 'snr-external',
       and 'cycle-slip-indicator' to 'container modem'.";
    reference
      "Waveserver OS R2.0.3 user's guide.";
  }
  revision 2020-05-12 {
    description
      "Added '500' to 'leaf reach-limit' range.";
    reference
      "Waveserver OS R2.0.1 user's guide.";
  }
  revision 2020-03-10 {
    description
      "Add 'WaveLogic 5e' to 'when' statements for augmentation.
       Changed 'leaf baud-rate' to 'leaf symbol-rate'.";
    reference
      "Waveserver OS R2.0 user's guide.";
  }
  revision 2019-08-15 {
    description
      "Added leaves 'tx-dispersion-precompensation-max' and 'tx-dispersion-
             precompensation-min' in 'modem' container.
       Updated range and description for 'reach-limit' and description for 'actual-reach' to
             reflect new 250km terrestrial reach license.";
    reference
      "Waveserver Ai R1.5 user's guide.";
  }
  revision 2018-11-16 {
    description
      "Updated range for 'tx-dispersion-precompensation-value'.
       Added leaf 'tx-dispersion-search-mode-min' in 'modem' container.
       Added leaf 'tx-dispersion-search-mode-max' in 'modem' container.";
    reference
      "Waveserver Ai R1.4 user's guide.";
  }
  revision 2018-06-22 {
    description
      "Added 'expected-restoration-time', 'far-end-class', 'actual-reach', and 'actual-link-optimization-mode' to modem container.
       Added 'supported-3dbm-signal-bandwidth' and 'supported-10dbm-signal-bandwidth' to modem container.
       Added 'actual' leafs to frequency and power containers.
       Changed 'estimated-instance-of-differential-group-delay' and 'mean-supported-differential-group-delay' from integer to decimal type.
       Added 'fast' laser-tuning-mode enum value.
       Updated ranges for 'tx-dispersion-precompensation-value' and 'tx-path-dispersion-value'.
       Added 'search' enum value to 'tx-dispersion-compensation-mode'.";
    reference
      "Waveserver Ai R1.2 user's guide.";
  }
  revision 2018-01-15 {
    description
      "Updated range and description for 'reach-limit' to match actual accepted values.";
    reference
      "Waveserver Ai R1.1 user's guide.";
  }
  revision 2017-08-10 {
    description
      "Waveserver Platform Data Model
       Migrated from Waveserver Classic R1.4 YANG model.
       Updated namespace to 'ciena-waveserver'.
       Removed WL3e-specific attributes ('performance-optimization-mode', 'interleaver-mode', 'rotation', 'tx-reduction-mode', 'differential-encoding', 'fast-rx-recovery').
       Removed obsolete attribute 'fast-receiver-recovery-state'.
       Removed 'band-plan' and some line-system related attributes.
       Removed 'actual' frequency.
       Removed 'performance-statistics' container, which will be represented in the ciena-waveserver-pm module in 'untimed' bins.
       Removed 'alarms' and 'diagnostics' containers.
       Renamed 'tx-tuning-mode' to 'laser-tuning-mode', and value 'performance-optimized' value to 'normal'.
       Renamed 'carrier-centering-mode' to 'laser-centering-mode'.
       Renamed/updated several dispersion compensation attributes for WLAi.
       Updated 'channel-contention-detection-avoidance' type from on/off to enabled/disabled.
       Moved 'colourless-rx-channel' attributes to lane/rx/power/optical-channel-power.
       Added several WLAi modem-specific attributes.";
    reference
      "Waveserver Ai R1.0 user's guide.";
  }

  augment "/ptp:waveserver-ptps/ptp:ptps/ptp:properties/ptp:transmitter" {
    ddf:ddf-struct-version "WlPropsTrans";
    when "../ptp:xcvr-type = 'WaveLogic Ai' or ../ptp:xcvr-type = 'WaveLogic 5e' or ../ptp:is-coherent = 'true'" {
      description
        "PTP transmitter properties specific to coherent line PTPs, such as the
         WaveLogic Ai and WaveLogic 5e fixed modem and the WL5n/400-ZR (QSFP-DD)
         pluggable line PTPs.";
    }
    description
      "PTP transmitter properties specific to coherent line PTPs.";
    container frequency {
      ui:ui-name "Tx Frequency";
      description
        "Tx Frequency attributes.";
      leaf value {
        ui:ui-name "Tx Frequency Value (GHz)";
        type cienawstypes:modem-frequency;
        units "GHz";
        description
          "The configured modem frequency value (GHz).";
      }

      leaf min-value {
        ui:ui-name "Frequency Min Value (GHz)";
        type cienawstypes:modem-frequency;
        units "GHz";
        config false;
        description
          "The minimum supported frequency value, in GHz.";
      }

      leaf max-value {
        ui:ui-name "Frequency Max Value (GHz)";
        type cienawstypes:modem-frequency;
        units "GHz";
        config false;
        description
          "The maximum supported frequency value, in GHz.";
      }

      leaf actual {
        ui:ui-name "Actual Tx Frequency Value (GHz)";
        type cienawstypes:modem-frequency;
        units "GHz";
        config false;
        description
          "The actual transmitter frequency value applied on the modem (GHz).";
      }
    }

    container power {
      ui:ui-name "Tx Power";
      description
        "Tx Power attributes.";
      leaf value {
        ui:ui-name "Tx Power Level (dBm)";
        type cienawstypes:tx-power-lvl;
        units "dBm";
        description
          "The provisioned transmit power in dBm.";
      }

      leaf min-value {
        ui:ui-name "Power Level Min Value (dBm)";
        type cienawstypes:decimal-1-dig;
        units "dBm";
        config false;
        description
          "The minimum supported tx power value, in dBm.";
      }

      leaf max-value {
        ui:ui-name "Power Level Max Value (dBm)";
        type cienawstypes:decimal-1-dig;
        units "dBm";
        config false;
        description
          "The maximum supported tx power value, in dBm.";
      }

      leaf actual {
        ui:ui-name "Actual Tx Power Level (dBm)";
        type cienawstypes:tx-power-lvl;
        units "dBm";
        config false;
        description
          "The actual optical transmit power value, in dBm.";
      }
    }
  }

  augment "/ptp:waveserver-ptps/ptp:ptps/ptp:properties" {
    ddf:ddf-struct-version "WlPropC";
    when "ptp:xcvr-type = 'WaveLogic Ai' or ptp:xcvr-type = 'WaveLogic 5e' or ptp:is-coherent = 'true'" {
      description
        "PTP properties specific to WaveLogic Ai and WaveLogic 5e modem.";
    }
    description
      "PTP properties specific to WaveLogic Ai and WaveLogic 5e modem.";
    container line-system {
      ui:ui-name "Line System";
      description
        "Line System related attributes.";
      leaf type {
        ui:ui-name "Line System Type";
        type cienawstypes:line-sys-enum;
        description
          "Line system type. Default is coloured";
      }
    }

    container modem {
      ui:ui-name "Modem";
      description
        "PTP Modem configuration and operational attributes.";
      leaf symbol-rate {
        ui:ui-name "Symbol Rate";
        type uint32;
        units "Gbaud";
        config false;
        description
          "The symbol rate value, based off the mode of the parent XCVR.";
      }

      leaf class {
        ui:ui-name "Modem Class";
        type cienawstypes:modem-class;
        description
          "The modem class type, terrestrial or submarine. Configuration requires
           proper license installed.";
      }

      leaf far-end-class {
        ui:ui-name "Far-End Modem Class";
        type cienawstypes:modem-class;
        config false;
        description
          "The modem class type on the remote end of the line, terrestrial or
           submarine, if available.";
      }

      leaf reach-limit {
        ui:ui-name "Reach Limit";
        type int16 {
          range "0|250|500|1000|2000|2100|3000|3500|4000|5000|8000|9000|14000";
        }
        units "km";
        description
          "The maximum reach allowed in km. The possible values are [250, 500, 1000, 2000,
           2100, 3000, 4000, 5000, 8000] for terrestrial modem class, and [3500, 9000, 14000] for
           submarine modem class. Configuration requires proper license installed.
           [0] if the value is unknown/unavailable or inapplicable.";
      }

      leaf actual-reach {
        ui:ui-name "Actual Reach";
        type int16;
        units "km";
        config false;
        description
          "Estimated actual reach in km. The possible values are [250, 500, 1000, 2000, 2100,
           3000, 4000, 5000, 8000] for terrestrial modem class, and [3500, 9000, 14000] for
           submarine modem class. Configuration requires proper license installed.
           [0] if the value is unknown/unavailable or inapplicable.";
      }

      leaf link-optimization-mode {
        ui:ui-name "Link Optimization Mode";
        type cienawstypes:link-optimization-mode;
        description
          "Link Optimization Mode. Default is standard.";
      }

      leaf actual-link-optimization-mode {
        ui:ui-name "Actual Link Optimization Mode";
        type cienawstypes:link-optimization-mode;
        config false;
        description
          "Actual Link Optimization mode applied on the modem, if available.";
      }

      leaf laser-tuning-mode {
        ui:ui-name "Laser Tuning Mode";
        type enumeration {
          enum "normal" {
            description
              "Normal (performance-optimized) laser tuning mode.";
          }
          enum "accelerated" {
            description
              "Accelerated laser tuning mode.";
          }
          enum "fast" {
            description
              "Fast laser tuning mode.";
          }
        }
        description
          "This is the Tuning Mode, which can be set as normal (performance-
           optimized), accelerated, or fast tuning mode. Default is normal.";
      }

      leaf laser-centering-mode {
        ui:ui-name "Laser Centering Mode";
        type enumeration {
          enum "disabled" {
            description
              "Laser centering disabled.";
          }
          enum "enabled" {
            description
              "Laser centering enabled.";
          }
          enum "holdover" {
            description
              "Laser centering in holdover mode.";
          }
        }
        description
          "This parameter is used to configure which laser centering mode to
           apply to the OTM signal.";
      }

      leaf laser-centering-range {
        ui:ui-name "Laser Centering Range";
        type decimal64 {
          fraction-digits 1;
          range "0.0 .. 3.0";
        }
        units "GHz";
        description
          "This parameter is used to configure the laser centering range.";
      }

      leaf laser-shutdown-mode {
        ui:ui-name "Laser Shutdown Mode";
        type enumeration {
          enum "accelerated" {
            description
              "Laser shutdown accelerated mode.";
          }
          enum "normal" {
            description
              "Laser shutdown normal mode.";
          }
        }
        description
          "Laser shutdown mode.";
      }

      leaf expected-restoration-time {
        ui:ui-name "Expected Restoration Time";
        type uint32 {
          range "0..1800";
        }
        units "seconds";
        description
          "Expected link restoration time, in seconds. Prevents the laser from
           dithering for a given period of time after traffic loss in order to
           minimize re-acquisition time. Default is 10 seconds.";
      }

      leaf channel-contention-detection-avoidance {
        ui:ui-name "Channel Contention Detection and Avoidance";
        type cienawstypes:enabled-disabled-enum;
        description
          "Enables or disables the channel contention detection and avoidance
           feature. This feature is used to detect the situation where the modem
           port turns on a wavelength (or frequency in Gridless mode) that is in
           use by an existing L0 connection on a colorless network. This feature
           will be triggered by new frequency provisioning and will automatically
           detects if the provisioned frequency is already used. If the
           provisioned frequency is already used, it declares channel contention,
           and then it will hold the Line port TX in a low power state (<-35 dBm)
           and will raise a Channel Contention alarm. This feature will also
           provide a mechanism to allow user to manually release the Line port TX
           from being held in a low power state while the channel collision
           declared.";
      }

      leaf channel-contention-threshold {
        ui:ui-name "Channel Contention Threshold";
        type decimal64 {
          fraction-digits 1;
          range "-30.0 .. 5.0";
        }
        units "dBm";
        description
          "Minimum Rx channel power above which the incoming signal shall be
           evaluated for channel contention.";
      }

      leaf tx-power-reduction-state {
        ui:ui-name "Tx Power Reduction State";
        type cienawstypes:enabled-disabled-enum;
        description
          "This parameter is used to enable Tx blanking functionality. Default is
           Disabled.";
      }

      leaf tx-dispersion-compensation-mode {
        ui:ui-name "Tx Dispersion Compensation Mode";
        type enumeration {
          enum "automatic" {
            description
              "Automatic Tx dispersion compensation management mode. This is the
               default.";
          }
          enum "fixed" {
            description
              "Fixed Tx dispersion compensation management mode.";
          }
          enum "search" {
            description
              "Search Tx dispersion compensation management mode.";
          }
          enum "adaptive" {
            description
              "Adaptive Tx dispersion compensation management mode.";
          }
        }
        description
          "Tx dispersion compensation management mode.";
      }

      leaf actual-tx-path-dispersion-value {
        ui:ui-name "Actual Tx Path Dispersion";
        type int32;
        units "ps/nm";
        config false;
        description
          "Total actual Tx Path dispersion value, in ps/nm.";
      }

      leaf tx-dispersion-precompensation-value {
        ui:ui-name "Tx Dispersion Pre-Compensation Value";
        type int32 {
          range "-44500..1000000";
        }
        units "ps/nm";
        description
          "Tx compensation dispersion value, in ps/nm. Default is 0 for automatic
           mode.";
      }

      leaf tx-dispersion-precompensation-min {
        ui:ui-name "Tx Dispersion Pre-Compensation Minimum Value";
        type int32 {
          range "-44500..1000000";
        }
        units "ps/nm";
        description
          "Tx compensation dispersion minimum value, in ps/nm.";
      }

      leaf tx-dispersion-precompensation-max {
        ui:ui-name "Tx Dispersion Pre-Compensation Maximum Value";
        type int32 {
          range "-44500..1000000";
        }
        units "ps/nm";
        description
          "Tx compensation dispersion maximum value, in ps/nm.";
      }

      leaf tx-path-dispersion-value {
        ui:ui-name "Tx Path Dispersion Value";
        type int32 {
          range "-89000..1044500";
        }
        units "ps/nm";
        description
          "Tx path dispersion value, in ps/nm.";
      }

      leaf tx-dispersion-min {
        ui:ui-name "Tx Dispersion Min Value";
        type int32;
        units "ps/nm";
        config false;
        description
          "Tx dispersion minimum value, in ps/nm.";
      }

      leaf tx-dispersion-max {
        ui:ui-name "Tx Dispersion Max Value";
        type int32;
        units "ps/nm";
        config false;
        description
          "Tx dispersion maximum value, in ps/nm.";
      }

      leaf tx-dispersion-search-mode-min {
        ui:ui-name "Tx Dispersion Search Mode Min Value";
        type int32 {
          range "-89000..1044500";
        }
        units "ps/nm";
        description
          "Minimum path dispersion sweeping range when operating in search mode,
           in ps/nm.";
      }

      leaf tx-dispersion-search-mode-max {
        ui:ui-name "Tx Dispersion Search Mode Max Value";
        type int32 {
          range "-89000..1044500";
        }
        units "ps/nm";
        description
          "Maximum path dispersion sweeping range when operating in search mode,
           in ps/nm.";
      }

      leaf actual-tx-link-dispersion {
        ui:ui-name "Actual Tx Link Dispersion";
        type int32;
        units "ps/nm";
        config false;
        description
          "Total actual Tx link dispersion, in ps/nm.";
      }

      leaf actual-rx-link-dispersion {
        ui:ui-name "Actual Rx Link Dispersion";
        type int32;
        units "ps/nm";
        config false;
        description
          "Total actual Rx link dispersion, in ps/nm.";
      }

      leaf actual-tx-precompensation-dispersion {
        ui:ui-name "Actual Tx Precompensation Dispersion";
        type int32;
        units "ps/nm";
        config false;
        description
          "Actual Tx precompensation dispersion value, in ps/nm. This is the
           total link dispersion in the near-to-far direction.";
      }

      leaf rx-post-compensation-dispersion {
        ui:ui-name "Rx Post-compensation Dispersion";
        type int32;
        units "ps/nm";
        config false;
        description
          "Rx post-compensation dispersion, in ps/nm.";
      }

      leaf estimated-instance-of-differential-group-delay {
        ui:ui-name "Estimated Instance of Differential Group Delay";
        type cienawstypes:decimal-3-dig;
        units "ps";
        config false;
        description
          "Estimated instance of differential group delay, in picoseconds (ps).";
      }

      leaf mean-supported-differential-group-delay {
        ui:ui-name "Mean Supported Differential Group Delay";
        type cienawstypes:decimal-3-dig;
        units "ps";
        config false;
        description
          "Mean supported differential group delay, in picoseconds (ps).";
      }

      leaf estimated-round-trip-delay {
        ui:ui-name "Estimated Round Trip Delay";
        type uint32;
        units "us";
        config false;
        description
          "Estimated round trip delay, in microseconds (us).";
      }

      leaf estimated-unidirectional-latency {
        ui:ui-name "Estimated Unidirectional Latency";
        type uint32;
        units "us";
        config false;
        description
          "Estimated unidirectional latency, in microseconds (us).";
      }

      leaf estimated-fiber-length {
        ui:ui-name "Estimated Fiber Length";
        type uint32;
        units "km";
        config false;
        description
          "Estimated fiber length, in kilometers (km).";
      }

      leaf min-spectral-width {
        ui:ui-name "Minimum Spectral Width";
        type cienawstypes:decimal-1-dig;
        units "GHz";
        config false;
        description
          "Minimum spectral width, in GHz.";
      }

      leaf supported-3dbm-signal-bandwidth {
        ui:ui-name "Supported 3 dBm Signal Bandwidth";
        type cienawstypes:decimal-1-dig;
        units "GHz";
        config false;
        description
          "Supported 3 dBm signal bandwidth, in GHz.";
      }

      leaf supported-10dbm-signal-bandwidth {
        ui:ui-name "Supported 10 dBm Signal Bandwidth";
        type cienawstypes:decimal-1-dig;
        units "GHz";
        config false;
        description
          "Supported 10 dBm signal bandwidth, in GHz.";
      }

      leaf regen-mate {
        type string {
          length "1..32";
        }
        config false;
        description
          "Mate information for the regen.
           The format is <slot>/<major> and should not be changed.";
      }

      leaf line-fail {
        type cienawstypes:line-fail-type;
        description
          "Line Fail leaf to control the contributors to SSF.";
      }
    }
  }

  augment "/ptp:waveserver-ptps/ptp:ptps/ptp:properties/ptp:lanes/ptp:lane/ptp:rx/ptp:power" {
    ddf:ddf-struct-version "WlRxChanPwr";
    when "../../../../ptp:xcvr-type = 'WaveLogic Ai' or ../../../../ptp:xcvr-type = 'WaveLogic 5e' or ../../../../ptp:is-coherent = 'true'" {
      description
        "PTP Rx power properties specific to WaveLogic Ai and WaveLogic 5e modem.";
    }
    description
      "PTP Rx power properties specific to WaveLogic Ai and WaveLogic 5e modem.";
    container optical-channel-power {
      ui:ui-name "Optical Channel Rx Power";
      config false;
      description
        "The actual Rx power attributes for the channel to which the receiver
         is tuned. For PTPs that support OPS protection, this reflects the
         active path only.";
      uses xcvr:optical-power-group;
    }
  }

  augment "/ptp:waveserver-ptps/ptp:ptps/ptp:properties/ptp:lanes/ptp:lane/ptp:rx/ptp:status" {
    ddf:ddf-struct-version "WlRxChanStatus";
    when "../../../../ptp:xcvr-type = 'WaveLogic Ai' or ../../../../ptp:xcvr-type = 'WaveLogic 5e' or ../../../../ptp:is-coherent = 'true'" {
      description
        "PTP Rx status properties specific to WaveLogic Ai and WaveLogic 5e modem.";
    }
    description
      "PTP Rx status properties specific to WaveLogic Ai and WaveLogic 5e modem.";
    container optical-channel-power {
      ui:ui-name "Optical Channel Rx Status";
      config false;
      description
        "Optical Channel Rx Power high/low alarm/warning status/thresholds,
         where applicable for the XCVR type.";
      uses xcvr:optical-power-status-group;

      uses xcvr:optical-power-threshold-group;

      leaf loss-of-signal {
        ui:ui-name "Rx Loss of Optical Channel";
        type boolean;
        description
          "Rx Loss of Optical Channel.";
      }
    }
  }
}
